MM200-MIB DEFINITIONS ::= BEGIN

	IMPORTS
		enterprises
			FROM RFC1155-SMI
		MODULE-IDENTITY, OBJECT-TYPE
			FROM SNMPv2-SMI;

mm200 MODULE-IDENTITY
	LAST-UPDATED "200111281000Z"
	ORGANIZATION "Radyne Comstream Inc."
	CONTACT-INFO
			"Customer Service
			Postal: RadyneComstream, Inc. - Phoenix.
			3138 E. Elwood Street
			Phoenix, AZ 85034
			USA

			Tel: (602) 437-9620
			Fax: (602) 437-4811

			Email: xxxx@radynecomstream.com"

	DESCRIPTION
			"RadyneComstream MM200 MIB module."

	REVISION   "200109051000Z"
	DESCRIPTION  "Initial version of the RadyneComstream MM200
               MIB module. This is a PRILIMINARY document whose contents
               are subject to change without prior notice. MM200 MIB
               Object Identifiers description. The privite entereprise
               number 2591 is a unique identifier assigned to Radyne
               by the Internet Assigned Numbers Authority (IANA).
               This number is used to uniquely define vendor specific
               information such as private MIBs."

	::= { radyne 11 }


-- groups in Radyne specific MIB

		radyne		OBJECT IDENTIFIER ::= { enterprises 2591 }

		mm200MIBObjects	OBJECT IDENTIFIER ::= { mm200 1 }
		radMM200ModNVStatus	OBJECT IDENTIFIER ::= { mm200MIBObjects 1 }
		radMM200ModStatus	OBJECT IDENTIFIER ::= { mm200MIBObjects 2 }

		radMM200DemodNVStatus OBJECT IDENTIFIER ::= { mm200MIBObjects 7 }
		radMM200DemodStatus	OBJECT IDENTIFIER ::= { mm200MIBObjects 8 }

		radMM200CommonNVStatus OBJECT IDENTIFIER ::= { mm200MIBObjects 13 }
		radMM200CommonStatus	OBJECT IDENTIFIER ::= { mm200MIBObjects 14 }

		radMM200MIBTraps	OBJECT IDENTIFIER ::= { mm200MIBObjects 15 }

		mm200MIBConformance	OBJECT IDENTIFIER ::= { mm200 2 }
		mm200Groups		OBJECT IDENTIFIER ::= { mm200MIBConformance 1 }
		mm200AgentCapabilities	OBJECT IDENTIFIER ::= { mm200MIBConformance 2 }

-- -------------------------------------------------------------------------------------------------------------------
-- Textual Conventions

ControlType ::= TEXTUAL-CONVENTION
	STATUS	current
	DESCRIPTION	"Represents a boolean control value."
	SYNTAX	INTEGER { disable(1), enable(2) }

InversionType ::= TEXTUAL-CONVENTION
	STATUS	current
	DESCRIPTION	"Represents a boolean inversion value."
	SYNTAX	INTEGER { normal(1), inverted(2) }

AlarmByteType ::= TEXTUAL-CONVENTION
	STATUS	current
	DESCRIPTION	"Represents a one byte integer value. Limits are 0 to 255"
	SYNTAX	INTEGER (0..255)

-- -------------------------------------------------------------------------------------------------------------------
-- -------------------------------------------------------------------------------------------------------------------
-- MM200 modulator non-volatile status information.

	radMM200TxCarrierControl OBJECT-TYPE
		SYNTAX	INTEGER {
				off(1),
				on(2)
				}
		MAX-ACCESS	read-write
		STATUS	current
		DESCRIPTION
				"Turns carrier on and off"
		::= { radMM200ModNVStatus 1 }

	radMM200TxTransmitPower OBJECT-TYPE
		SYNTAX	INTEGER (-200..0)
		MAX-ACCESS	read-write
		STATUS	current
		DESCRIPTION
				"Selects the Tx power level in dBm from +0.0 to -20.0. There is an
				implied decimal point. For example a value of -39 represents a
				transmit power level of -3.9 dBm."
		::= { radMM200ModNVStatus 2 }

	radMM200TxIFFrequency OBJECT-TYPE
		SYNTAX	INTEGER (50000000..90000000)
		MAX-ACCESS	read-write
		STATUS	current
		DESCRIPTION
				"Selects IF frequency in Hz. This is the center frequency of the
				aggregate; the edge frequency, however, is dependent on the number
				of channels, symbol rate, and spacing. The frequency range of the
				MM200 is 50MHz to 90MHz."
		::= { radMM200ModNVStatus 3 }

	radMM200TxIFUser1Frequency OBJECT-TYPE
		SYNTAX	INTEGER (50000000..90000000)
		MAX-ACCESS	read-write
		STATUS	current
		DESCRIPTION
				"Selects IF user 1 frequency in Hz."
		::= { radMM200ModNVStatus 4 }

	radMM200TxIFUser2Frequency OBJECT-TYPE
		SYNTAX	INTEGER (50000000..90000000)
		MAX-ACCESS	read-write
		STATUS	current
		DESCRIPTION
				"Selects IF user 2 frequency in Hz."
		::= { radMM200ModNVStatus 5 }

	radMM200TxIFUser3Frequency OBJECT-TYPE
		SYNTAX	INTEGER (50000000..90000000)
		MAX-ACCESS	read-write
		STATUS	current
		DESCRIPTION
				"Selects IF user 3 frequency in Hz."
		::= { radMM200ModNVStatus 6 }

	radMM200TxIFUser4Frequency OBJECT-TYPE
		SYNTAX	INTEGER (50000000..90000000)
		MAX-ACCESS	read-write
		STATUS	current
		DESCRIPTION
				"Selects IF user 4 frequency in Hz."
		::= { radMM200ModNVStatus 7 }

	radMM200TxIFSeperation OBJECT-TYPE
		SYNTAX	INTEGER (100..150)
		MAX-ACCESS	read-write
		STATUS	current
		DESCRIPTION
				"Selects IF frequency separation in percent. It is the additional
				bandwidth percentage the carrier will cover over the original symbol
				rate. The range is 100% to 150%."
		::= { radMM200ModNVStatus 8 }

	radMM200TxDataRate OBJECT-TYPE
		SYNTAX	INTEGER (7000000..200000000)
		MAX-ACCESS	read-write
		STATUS	current
		DESCRIPTION
				"Selects the data rate in BPS. The data rate is variable from 7 Mbps
				to 200 Mbps."
		::= { radMM200ModNVStatus 9 }

	radMM200TxSymbolRate OBJECT-TYPE
		SYNTAX	INTEGER (3500000..28000000)
		MAX-ACCESS	read-write
		STATUS	current
		DESCRIPTION
				"Selects the symbol rate in SPS. The symbol rate is variable from 3.5Msps to 28Msps."
		::= { radMM200ModNVStatus 10 }

	radMM200TxModulation OBJECT-TYPE
		SYNTAX	INTEGER {
				qam4(1),
				qam16(2),
				qam32(3),
				qam64(4),
				qam128(5),
				qam256(6)
				}
		MAX-ACCESS	read-write
		STATUS	current
		DESCRIPTION
				"Selects the QAM modulation type."
		::= { radMM200ModNVStatus 11 }

	radMM200TxSpectrum OBJECT-TYPE
		SYNTAX	InversionType
		MAX-ACCESS	read-write
		STATUS	current
		DESCRIPTION
				"Inverts the direction of rotation for the modulation."
		::= { radMM200ModNVStatus 12 }

	radMM200TxCarrierMode OBJECT-TYPE
		SYNTAX	INTEGER {
               normal(1),
               cw(2),
               offset1hz(3),
               khz100(4),
               mhz35(5),
               sweepUp(6),
               sweepDown(7)
             }
		MAX-ACCESS	read-write
		STATUS	current
		DESCRIPTION
             "Normal sets the carrier to normal
              CW causes the modulator to output pure carrier
              Offset 1Hz
              100 KHz
              3.5 MHz
              Sweep up
              Sweep down"
		::= { radMM200ModNVStatus 13 }

	radMM200TxChannelSetting OBJECT-TYPE
		SYNTAX	INTEGER {
               oneChannel(2),
               twoChannel(3),
               threeChannel(4),
               fourChannel(5)
             }
		MAX-ACCESS	read-write
		STATUS	current
		DESCRIPTION
             "Selects the total number of channels in the MM200.
              Automatic selection allows the MM200 to use the
              maximum number of channels."
		::= { radMM200ModNVStatus 14 }

	radMM200TxMajorAlarm1Mask OBJECT-TYPE
		SYNTAX	AlarmByteType
		MAX-ACCESS	read-write
		STATUS	current
		DESCRIPTION
             "Major Alarm 1 mask:
              Bit 0 = Glue logic FPGA fail
              Bit 1 = Data FPGA fail
              Bit 2-7 = Spares
              0 = Mask, 1 = Allow"
		::= { radMM200ModNVStatus 15 }

	radMM200TxMajorAlarm2Mask OBJECT-TYPE
		SYNTAX	AlarmByteType
		MAX-ACCESS	read-write
		STATUS	current
		DESCRIPTION
             "Major Alarm 2 mask:
              Bit 0-7 = Spares
              0 = Mask, 1 = Allow"
		::= { radMM200ModNVStatus 16 }

	radMM200TxMinorAlarm1Mask OBJECT-TYPE
		SYNTAX	AlarmByteType
		MAX-ACCESS	read-write
		STATUS	current
		DESCRIPTION
             "Minor Alarm 1 mask:
              Bit 0 = Tx clock activity detect
              Bit 1 = Tx data activity detect
              Bit 2 = Frame lock
              Bit 3 = Spare
              Bit 4 = Spare
              Bit 5 = Spare
              Bit 6 = Spare
              Bit 7 = Spare
              0 = Mask, 1 = Allow"
		::= { radMM200ModNVStatus 17 }

	radMM200TxMinorAlarm2Mask OBJECT-TYPE
		SYNTAX	AlarmByteType
		MAX-ACCESS	read-write
		STATUS	current
		DESCRIPTION
             "Minor Alarm 2 mask:
              Bit 0..7 = Spares
              0 = Mask, 1 = Allow"
		::= { radMM200ModNVStatus 18 }

	radMM200TxPRBS OBJECT-TYPE
		SYNTAX	INTEGER {
               normal(1),
               prbs23(2),
               prbs23m(3),
               prbs15(4),
               prbs15m(5)
             }
		MAX-ACCESS	read-write
		STATUS	current
		DESCRIPTION
             "Selects the pseudo-random bit sequence for link
              testing."
		::= { radMM200ModNVStatus 19 }


-- --------------------------------------------------------------------------------------------------------------------
-- --------------------------------------------------------------------------------------------------------------------
-- MM200 modulator status information.

	radMM200TxMajorAlarm1Status OBJECT-TYPE
		SYNTAX	AlarmByteType
		MAX-ACCESS	read-only
		STATUS	current
		DESCRIPTION
             "A bit field. On startup, the agent initializes this
              to the value '00000000'B
              Bit 0 = Glue logic FPGA fail
              Bit 1 = Data FPGA fail
              Bit 2-7 = Spares
              0 = Pass, 1 = Fail"
		::= { radMM200ModStatus 1 }

	radMM200TxMajorAlarm2Status OBJECT-TYPE
		SYNTAX	AlarmByteType
		MAX-ACCESS	read-only
		STATUS	current
		DESCRIPTION
             "A bit field. On startup, the agent initializes this to
              the value '00000000'B
              Bit 0..7 = Spares
              0 = Pass, 1 = Fail"
		::= { radMM200ModStatus 2 }

	radMM200TxMinorAlarm1Status OBJECT-TYPE
		SYNTAX	AlarmByteType
		MAX-ACCESS	read-only
		STATUS	current
		DESCRIPTION
             "A bit field. On startup, the agent initializes this to
              the value '00000000'B
              Bit 0 = Tx clock activity detect
              Bit 1 = Tx data activity detect
              Bit 2 = Frame lock
              Bit 3 = Spare
              Bit 4 = Spare
              Bit 5 = Spare
              Bit 6 = Spare
              Bit 7 = Spare
              0 = Pass, 1 = Fail"
		::= { radMM200ModStatus 3 }

	radMM200TxMinorAlarm2Status OBJECT-TYPE
		SYNTAX	AlarmByteType
		MAX-ACCESS	read-only
		STATUS	current
		DESCRIPTION
             "A bit field. On startup, the agent initializes this to
              the value '00000000'B
              Bit 0..7 = Spares
              0 = Pass, 1 = Fail"
		::= { radMM200ModStatus 4 }

	radMM200TxLatchedMajorAlarm1Status OBJECT-TYPE
		SYNTAX	AlarmByteType
		MAX-ACCESS	read-only
		STATUS	current
		DESCRIPTION
             "A bit field. On startup, the agent initializes this
              to the value '00000000'B.
              Bit 0 = Glue logic FPGA fail
              Bit 1 = Data FPGA fail
              Bit 2-7 = Spares
              0 = Pass, 1 = Fail"
		::= { radMM200ModStatus 5 }

	radMM200TxLatchedMajorAlarm2Status OBJECT-TYPE
		SYNTAX 	AlarmByteType
		MAX-ACCESS	read-only
		STATUS	current
		DESCRIPTION
             "A bit field. On startup, the agent initializes this to
              the value '00000000'B.
              Bit 0..7 = Spares
              0 = Pass, 1 = Fail"
		::= { radMM200ModStatus 6 }

	radMM200TxLatchedMinorAlarm1Status OBJECT-TYPE
		SYNTAX	AlarmByteType
		MAX-ACCESS	read-only
		STATUS	current
		DESCRIPTION
             "A bit field. On startup, the agent initializes this to
              the value '00000000'B.
              Bit 0 = Tx clock activity detect
              Bit 1 = Tx data activity detect
              Bit 2 = Frame lock
              Bit 3 = Spare
              Bit 4 = Spare
              Bit 5 = Spare
              Bit 6 = Spare
              Bit 7 = Spare
              0 = Pass, 1 = Fail"
		::= { radMM200ModStatus 7 }

	radMM200TxLatchedMinorAlarm2Status OBJECT-TYPE
		SYNTAX	AlarmByteType
		MAX-ACCESS	read-only
		STATUS	current
		DESCRIPTION
             "A bit field. On startup, the agent initializes this to
              the value '00000000'B.
              Bit 0..7 = Spares
              0 = Pass, 1 = Fail"
		::= { radMM200ModStatus 8 }

	radMM200TxCarrierStatus OBJECT-TYPE
		SYNTAX	INTEGER {
               off(1),
               on(2)
             }
		MAX-ACCESS	read-only
		STATUS	current
		DESCRIPTION
             "Shows status of the carrier, on or off"
		::= { radMM200ModStatus 9 }

	radMM200TxMaxPayload OBJECT-TYPE
		SYNTAX	INTEGER (0..200000000)
		MAX-ACCESS	read-only
		STATUS	current
		DESCRIPTION
             "Maximum payload at current modulation."
		::= { radMM200ModStatus 10 }

	radMM200TxPercentUtilization OBJECT-TYPE
		SYNTAX	INTEGER (0..65536)
		MAX-ACCESS	read-only
		STATUS	current
		DESCRIPTION
				"% utilization, implied decimal point.(i.e. 7985 means 79.85%"
		::= { radMM200ModStatus 11 }

	radMM200TxBandwidth OBJECT-TYPE
		SYNTAX	INTEGER (0..40000000)
		MAX-ACCESS	read-only
		STATUS	current
		DESCRIPTION
				"Current bandwidth usage."
		::= { radMM200ModStatus 12 }

-- -------------------------------------------------------------------------------------------------------------------
-- -------------------------------------------------------------------------------------------------------------------
-- MM200 modulator channel non-volatile status information.

	radMM200TxChannelNVStatusTable OBJECT-TYPE
		SYNTAX	SEQUENCE OF RadMM200TxChannelNVStatusEntry
		MAX-ACCESS	not-accessible
		STATUS	mandatory
		DESCRIPTION
				"MM200 Tx channel non-volatile status Table"
		::= { mm200MIBObjects 3 }

	radMM200TxChannelNVStatusEntry OBJECT-TYPE
		SYNTAX	RadMM200TxChannelNVStatusEntry
		MAX-ACCESS	not-accessible
		STATUS	current
		DESCRIPTION
				"MM200 Tx channel non-volatile status structure"
		INDEX	{ radMM200TxChannelNVIndex }
		::= { radMM200TxChannelNVStatusTable 1 }

	RadMM200TxChannelNVStatusEntry ::=
		SEQUENCE	{
			radMM200TxChannelNVIndex INTEGER,
			radMM200TxChannelMajorAlarmMask INTEGER,
			radMM200TxChannelMinorAlarmMask INTEGER
		}

	radMM200TxChannelNVIndex OBJECT-TYPE
		SYNTAX	INTEGER (1..4)
		MAX-ACCESS	read-only
		STATUS	current
		DESCRIPTION
				"Index into the MM200 Tx channel non-volatile table."
		::= { radMM200TxChannelNVStatusEntry 1 }

	radMM200TxChannelMajorAlarmMask OBJECT-TYPE
		SYNTAX	AlarmByteType
		MAX-ACCESS	read-write
		STATUS	current
		DESCRIPTION
				"Major Alarm mask:
				Bit 0 = Mod daughter board FPGA status
				Bit 1 = RF PLL lock detect status
				Bit 2-7 = Spares
				0 = Mask, 1 = Allow"
		::= { radMM200TxChannelNVStatusEntry 2 }

	radMM200TxChannelMinorAlarmMask OBJECT-TYPE
		SYNTAX	AlarmByteType
		MAX-ACCESS	read-write
		STATUS 	current
		DESCRIPTION
             "Minor Alarm mask:
              Bit 0 = Loop lock status
              Bit 1 = FEC lock status
              Bit 2 = FIFO full status
              Bit 3 = FIFO empty status
              Bit 4 = FIFO active
              Bit 5-7 = Spares
              0 = Mask, 1 = Allow"
		::= { radMM200TxChannelNVStatusEntry 3 }

-- --------------------------------------------------------------------------------------------------------------------
-- --------------------------------------------------------------------------------------------------------------------
-- MM200 modulator channel status information.

	radMM200TxChannelStatusTable OBJECT-TYPE
		SYNTAX	SEQUENCE OF RadMM200TxChannelStatusEntry
		MAX-ACCESS	not-accessible
		STATUS	mandatory
		DESCRIPTION
				"MM200 Tx channel volatile status Table"
		::= { mm200MIBObjects 4 }

	radMM200TxChannelStatusEntry OBJECT-TYPE
		SYNTAX	RadMM200TxChannelStatusEntry
		MAX-ACCESS	not-accessible
		STATUS	current
		DESCRIPTION
				"MM200 Tx channel volatile status structure"
		INDEX	{ radMM200TxChannelIndex }
		::= { radMM200TxChannelStatusTable 1 }

	RadMM200TxChannelStatusEntry ::=
		SEQUENCE	{
			radMM200TxChannelIndex INTEGER,
			radMM200TxChannelMajorAlarmStatus INTEGER,
			radMM200TxChannelMinorAlarmStatus INTEGER,
			radMM200TxChannelLatchedMajorAlarmStatus INTEGER,
			radMM200TxChannelLatchedMinorAlarmStatus INTEGER,
			radMM200TxChannelBaudRate INTEGER,
			radMM200TxChannelBaudState INTEGER
		}

	radMM200TxChannelIndex OBJECT-TYPE
		SYNTAX	INTEGER (1..4)
		MAX-ACCESS	read-only
		STATUS	current
		DESCRIPTION
				"Index into the MM200 Tx channel volatile table."
		::= { radMM200TxChannelStatusEntry 1 }

	radMM200TxChannelMajorAlarmStatus OBJECT-TYPE
		SYNTAX	AlarmByteType
		MAX-ACCESS	read-only
		STATUS	current
		DESCRIPTION
				"Major Alarm status:
				Bit 0 = Mod daughter board FPGA status
				Bit 1 = RF PLL lock detect status
				Bit 2-7 = Spares
				0 = PASS, 1 = FAIL"
		::= { radMM200TxChannelStatusEntry 2 }

	radMM200TxChannelMinorAlarmStatus OBJECT-TYPE
		SYNTAX	AlarmByteType
		MAX-ACCESS	read-only
		STATUS	current
		DESCRIPTION
			"Minor Alarm status:
			Bit 0 = Loop lock status
			Bit 1 = FEC lock status
			Bit 2 = FIFO full status
			Bit 3 = FIFO empty status
            Bit 4 = FIFO active
             Bit 5-7 = Spares
			0 = PASS, 1 = FAIL"
		::= { radMM200TxChannelStatusEntry 3 }

	radMM200TxChannelLatchedMajorAlarmStatus OBJECT-TYPE
		SYNTAX	AlarmByteType
		MAX-ACCESS	read-only
		STATUS	current
		DESCRIPTION
			"Major Alarm status:
			Bit 0 = Mod daughter board FPGA status
			Bit 1 = RF PLL lock detect status
			Bit 2-7 = Spares
			0 = PASS, 1 = FAIL"
		::= { radMM200TxChannelStatusEntry 4 }

	radMM200TxChannelLatchedMinorAlarmStatus OBJECT-TYPE
		SYNTAX	AlarmByteType
		MAX-ACCESS	read-only
		STATUS	current
		DESCRIPTION
             "Minor Alarm status:
              Bit 0 = Loop lock status
              Bit 1 = FEC lock status
              Bit 2 = FIFO full status
              Bit 3 = FIFO empty status
              Bit 4 = FIFO active
              Bit 5-7 = Spares
              0 = PASS, 1 = FAIL"
		::= { radMM200TxChannelStatusEntry 5 }

	radMM200TxChannelBaudRate OBJECT-TYPE
		SYNTAX	INTEGER (7000000..200000000)
		MAX-ACCESS	read-only
		STATUS	current
		DESCRIPTION
             "Tx channel baud rate"
		::= { radMM200TxChannelStatusEntry 6 }

	radMM200TxChannelBaudState OBJECT-TYPE
		SYNTAX 	INTEGER {
				clockSourcing(1),
				outOfLock(2),
      			losingLock(3),
				acquiring(4),
				locked(5),
				tooSlow(6),
				tooFast(7),
				searchingUp(8),
				searchingDown(9)
				}
		MAX-ACCESS	read-only
		STATUS	current
		DESCRIPTION
             "Tx channel baud state"
		::= { radMM200TxChannelStatusEntry 7 }

-- --------------------------------------------------------------------------------------------------------------------
-- --------------------------------------------------------------------------------------------------------------------
-- MM200 modulator interface non-volatile status information.

	radMM200TxInterfaceNVStatusTable OBJECT-TYPE
		SYNTAX	SEQUENCE OF RadMM200TxInterfaceNVStatusEntry
		MAX-ACCESS	not-accessible
		STATUS	mandatory
		DESCRIPTION
             "MM200 Tx interface non-volatile status Table"
		::= { mm200MIBObjects 5 }

	radMM200TxInterfaceNVStatusEntry OBJECT-TYPE
		SYNTAX	RadMM200TxInterfaceNVStatusEntry
		MAX-ACCESS	not-accessible
		STATUS	current
		DESCRIPTION
             "MM200 Tx interface non-volatile status structure"
		INDEX 	{ radMM200TxInterfaceNVIndex }
		::= { radMM200TxInterfaceNVStatusTable 1 }

	RadMM200TxInterfaceNVStatusEntry ::=
		SEQUENCE	{
			radMM200TxInterfaceNVIndex INTEGER,
			radMM200TxInterfacePID INTEGER,
			radMM200TxInterfaceDataRate INTEGER,
			radMM200TxInterfaceControl INTEGER,
			radMM200TxInterfaceType INTEGER,
			radMM200TxInterfaceSubType INTEGER,
			radMM200TxInterfaceFraming INTEGER,
			radMM200TxInterfaceVolume INTEGER,
			radMM200TxInterfaceClockPolarity INTEGER,
			radMM200TxInterfaceDataInvert INTEGER,
			radMM200TxInterfaceBasebandLoopback INTEGER,
			radMM200TxInterfacePRBS INTEGER,
			radMM200TxInterfaceMajorAlarmMask INTEGER,
			radMM200TxInterfaceMinorAlarmMask INTEGER
		}

	radMM200TxInterfaceNVIndex OBJECT-TYPE
		SYNTAX	INTEGER (1..4)
		MAX-ACCESS	read-only
		STATUS	current
		DESCRIPTION
             "Index into the MM200 Tx interface on-volatile table."
		::= { radMM200TxInterfaceNVStatusEntry 1 }

	radMM200TxInterfacePID OBJECT-TYPE
		SYNTAX	INTEGER (0..8192)
		MAX-ACCESS	read-write
		STATUS	current
		DESCRIPTION
             "Selects the interface Program Id. If not in 188 byte
              framing mode (unframed), this PID steers the packet to
              the appropriate interface. In the MM200, only one
              framed interface is allowed and its packets are sent in
              the clear, without modifications. The Null PID and the PIDs
              of the unframed interfaces should be unique. All packets
              PIDs not equal to these will be sent to the framed
              interface."
		::= { radMM200TxInterfaceNVStatusEntry 2 }

	radMM200TxInterfaceDataRate OBJECT-TYPE
		SYNTAX 	INTEGER (64000..200000000)
		MAX-ACCESS	read-write
		STATUS	current
		DESCRIPTION
             "Selects the data rate in BPS of the individual interfaces.
              The data rate is T3, E3, or STS1 for G.703
                    155.52M BPS for OC3 and STM1
                    1.544M BPS for T1
                    2.048M BPS for E1
                    Variable for parallel and ASI
                    64K BPS for 8 channel DS0
              The range is between 64K to 200M BPS"
		::= { radMM200TxInterfaceNVStatusEntry 3 }

	radMM200TxInterfaceControl OBJECT-TYPE
		SYNTAX	ControlType
		MAX-ACCESS	read-write
		STATUS	current
		DESCRIPTION
             "Controls the Tx interface."
		::= { radMM200TxInterfaceNVStatusEntry 4 }

	radMM200TxInterfaceType OBJECT-TYPE
		SYNTAX	INTEGER {
				asi(1),
				aasi(2),
				t3(3),
				e3(4),
				sts1(5),
				t1(6),
				e1(7),
				ds0x8(8),
				ds0x7A(9),
				parallelDVB(10),
				parallelM2P(11),
				oc3(12),
				stm1(13),
				hssi(14),
				smpt19(15),
				smpt38(16)
		   }
		MAX-ACCESS	read-write
		STATUS	current
		DESCRIPTION
             "Selects the Tx interface type."
		::= { radMM200TxInterfaceNVStatusEntry 5 }

	radMM200TxInterfaceSubType OBJECT-TYPE
		SYNTAX	INTEGER {
				spare(1),
				}
		MAX-ACCESS	read-write
		STATUS	current
		DESCRIPTION
             "Selects the Tx interface sub-type."
		::= { radMM200TxInterfaceNVStatusEntry 6 }

	radMM200TxInterfaceFraming OBJECT-TYPE
		SYNTAX	INTEGER {
               unframed(1),
			mpeg188(2),
               mpeg204(3)
             }
		MAX-ACCESS	read-write
		STATUS	current
		DESCRIPTION
             "Selects Unframed (184 Byte proprietary packet),
              MPEG Sync Byte and MPEG Sync Byte plus ReedSolomon."
		::= { radMM200TxInterfaceNVStatusEntry 7 }

	radMM200TxInterfaceVolume OBJECT-TYPE
		SYNTAX	INTEGER (0..255)
		MAX-ACCESS	read-write
		STATUS	current
		DESCRIPTION
             "Sets the volume on the audio channel on the DS0
              interfaces"
		::= { radMM200TxInterfaceNVStatusEntry 8 }

	radMM200TxInterfaceClockPolarity OBJECT-TYPE
		SYNTAX	INTEGER {
               normal(1),
               inverted(2),
             }
		MAX-ACCESS	read-write
		STATUS	current
		DESCRIPTION
             "Selects clock polarity for Tx terrestrial clock
              relative to Tx data."
		::= { radMM200TxInterfaceNVStatusEntry 9 }

	radMM200TxInterfaceDataInvert OBJECT-TYPE
		SYNTAX	InversionType
		MAX-ACCESS	read-write
		STATUS	current
		DESCRIPTION
             "Selects data polarity"
		::= { radMM200TxInterfaceNVStatusEntry 10 }

	radMM200TxInterfaceBasebandLoopback OBJECT-TYPE
		SYNTAX	ControlType
		MAX-ACCESS	read-write
		STATUS	current
		DESCRIPTION
             "Enables or disables Tx Interface Baseband Loopback."
		::= { radMM200TxInterfaceNVStatusEntry 11 }

	radMM200TxInterfacePRBS OBJECT-TYPE
		SYNTAX	INTEGER {
               normal(1),
               ones(2),
               pat001(3),
               prbs2047(4),
             }
		MAX-ACCESS	read-write
		STATUS	optional
		DESCRIPTION
             "Selects the pseudo-random bit sequence for Tx
              interface link testing. Not yet implemented."
		::= { radMM200TxInterfaceNVStatusEntry 12 }

	radMM200TxInterfaceMajorAlarmMask OBJECT-TYPE
		SYNTAX	AlarmByteType
		MAX-ACCESS	read-write
		STATUS	current
		DESCRIPTION
             "Major Alarm mask:
              Bit 0 = Interface test
              Bit 1-7 = Spares
              0 = Mask, 1 = Allow"
		::= { radMM200TxInterfaceNVStatusEntry 13 }

	radMM200TxInterfaceMinorAlarmMask OBJECT-TYPE
		SYNTAX	AlarmByteType
		MAX-ACCESS	read-write
		STATUS	current
		DESCRIPTION
             "Minor Alarm mask:
              Bit 0 = Interface FIFO full
              Bit 1 = Interface FIFO empty
              Bit 2 = Interface PLL lock
              Bit 3 = Interface data activity detect
              Bit 4 = Interface clock activity detect
              Bit 5 = Interface Tx input framing valid, added for AASI
              Bit 6 = Interface signal loss, valid for some interfaces
              Bit 7 = Spares
              0 = Mask, 1 = Allow"
		::= { radMM200TxInterfaceNVStatusEntry 14 }

-- ---------------------------------------------------------------------------------------------------------------------
-- ---------------------------------------------------------------------------------------------------------------------
-- MM200 modulator interface volatile status information.

	radMM200TxInterfaceStatusTable OBJECT-TYPE
		SYNTAX	SEQUENCE OF RadMM200TxInterfaceStatusEntry
		MAX-ACCESS	not-accessible
		STATUS	mandatory
		DESCRIPTION
             "MM200 Tx interface volatile status Table"
		::= { mm200MIBObjects 6 }

	radMM200TxInterfaceStatusEntry OBJECT-TYPE
		SYNTAX	RadMM200TxInterfaceStatusEntry
		MAX-ACCESS	not-accessible
		STATUS	current
		DESCRIPTION
             "MM200 Tx interface volatile status structure"
		INDEX    { radMM200TxInterfaceIndex }
		::= { radMM200TxInterfaceStatusTable 1 }

	RadMM200TxInterfaceStatusEntry ::=
		SEQUENCE	{
			radMM200TxInterfaceIndex INTEGER,
			radMM200TxInterfaceMajorAlarmStatus INTEGER,
			radMM200TxInterfaceMinorAlarmStatus INTEGER,
			radMM200TxInterfaceLatchedMajorAlarmStatus INTEGER,
			radMM200TxInterfaceLatchedMinorAlarmStatus INTEGER,
			radMM200TxInterfaceCard INTEGER
			}

	radMM200TxInterfaceIndex OBJECT-TYPE
		SYNTAX	INTEGER (1..4)
		MAX-ACCESS	read-only
		STATUS	current
		DESCRIPTION
             "Index into the MM200 Tx interface volatile table."
		::= { radMM200TxInterfaceStatusEntry 1 }

	radMM200TxInterfaceMajorAlarmStatus OBJECT-TYPE
		SYNTAX	AlarmByteType
		MAX-ACCESS	read-only
		STATUS	current
		DESCRIPTION
             "Major Alarm status:
              Bit 0 = Interface test
              Bit 1-7 = Spares
              0 = Pass, 1 = Fail"
		::= { radMM200TxInterfaceStatusEntry 2 }

	radMM200TxInterfaceMinorAlarmStatus OBJECT-TYPE
		SYNTAX	AlarmByteType
		MAX-ACCESS	read-only
		STATUS	current
		DESCRIPTION
             "Minor Alarm status:
              Bit 0 = Interface FIFO full
              Bit 1 = Interface FIFO empty
              Bit 2 = Interface PLL lock
              Bit 3 = Interface data activity detect
              Bit 4 = Interface clock activity detect
              Bit 5 = Interface Tx input framing valid, added for AASI
              Bit 6 = Interface signal loss, valid for some interfaces
              Bit 7 = Spares
              0 = Pass, 1 = Fail"
		::= { radMM200TxInterfaceStatusEntry 3 }

	radMM200TxInterfaceLatchedMajorAlarmStatus OBJECT-TYPE
		SYNTAX	AlarmByteType
		MAX-ACCESS	read-only
		STATUS	current
		DESCRIPTION
             "Major Alarm status:
              Bit 0 = Interface test
              Bit 1-7 = Spares
              0 = Pass, 1 = Fail"
		::= { radMM200TxInterfaceStatusEntry 4 }

	radMM200TxInterfaceLatchedMinorAlarmStatus OBJECT-TYPE
		SYNTAX	AlarmByteType
		MAX-ACCESS	read-only
		STATUS 	current
		DESCRIPTION
             "Minor Alarm status:
              Bit 0 = Interface FIFO full
              Bit 1 = Interface FIFO empty
              Bit 2 = Interface PLL lock
              Bit 3 = Interface data activity detect
              Bit 4 = Interface clock activity detect
              Bit 5 = Interface Tx input framing valid, added for AASI
              Bit 6 = Interface signal loss, valid for some interfaces
              Bit 7 = Spares
              0 = Pass, 1 = Fail"
		::= { radMM200TxInterfaceStatusEntry 5 }

	radMM200TxInterfaceCard OBJECT-TYPE
		SYNTAX	INTEGER {
				none(1),
				asi_aasi(2),
				nasi(3),
				t3e3(4),
				t1e1(5),
				ds0(6),
				parallel(7),
				oc3(8),
				hssi(9),
				smpte(10)
            	}
		MAX-ACCESS	read-only
		STATUS	current
		DESCRIPTION
				"Interface card type."
		::= { radMM200TxInterfaceStatusEntry 6 }

-- --------------------------------------------------------------------------------------------------------------------
-- --------------------------------------------------------------------------------------------------------------------
-- MM200 demodulator non-volatile status information.

	radMM200RxIFFrequency OBJECT-TYPE
		SYNTAX	INTEGER (50000000..90000000)
		MAX-ACCESS	read-write
		STATUS	current
		DESCRIPTION
             "Selects IF frequency in Hz. This is the center
              frequency of the aggregate; the edge frequency,
              however, is dependent on the number of channels,
              symbol rate, and spacing. The frequency range
              of the MM200 is 50MHz to 90MHz."
		::= { radMM200DemodNVStatus 1 }

	radMM200RxIFUser1Frequency OBJECT-TYPE
		SYNTAX	INTEGER (50000000..90000000)
		MAX-ACCESS	read-write
		STATUS	current
		DESCRIPTION
             "Selects IF user 1 frequency in Hz."
		::= { radMM200DemodNVStatus 2 }

	radMM200RxIFUser2Frequency OBJECT-TYPE
		SYNTAX	INTEGER (50000000..90000000)
		MAX-ACCESS	read-write
		STATUS	current
		DESCRIPTION
             "Selects IF user 2 frequency in Hz."
		::= { radMM200DemodNVStatus 3 }

	radMM200RxIFUser3Frequency OBJECT-TYPE
		SYNTAX	INTEGER (50000000..90000000)
		MAX-ACCESS	read-write
		STATUS	current
		DESCRIPTION
             "Selects IF user 3 frequency in Hz."
		::= { radMM200DemodNVStatus 4 }

	radMM200RxIFUser4Frequency OBJECT-TYPE
		SYNTAX	INTEGER (50000000..90000000)
		MAX-ACCESS	read-write
		STATUS	current
		DESCRIPTION
             "Selects IF user 4 frequency in Hz."
		::= { radMM200DemodNVStatus 5 }

	radMM200RxIFSeperation OBJECT-TYPE
		SYNTAX	INTEGER (100..150)
		MAX-ACCESS	read-write
		STATUS	current
		DESCRIPTION
             "Selects IF frequency separation in percent. It is
              the additional bandwidth percentage the carrier
              will cover over the original symbol rate. The range
              is 100% to 150%."
		::= { radMM200DemodNVStatus 6 }

	radMM200RxDataRate OBJECT-TYPE
		SYNTAX	INTEGER (7000000..200000000)
		MAX-ACCESS	read-write
		STATUS	current
		DESCRIPTION
             "Selects the data rate in BPS. The data rate is
              variable from 7 Mbps to 200 Mbps."
		::= { radMM200DemodNVStatus 7 }

	radMM200RxSymbolRate OBJECT-TYPE
		SYNTAX	INTEGER (3500000..28000000)
		MAX-ACCESS	read-write
		STATUS	current
		DESCRIPTION
             "Selects the data rate in BPS. The data rate is
              variable from 3.5Mbps to 28Mbps."
		::= { radMM200DemodNVStatus 8 }

	radMM200RxDemodulation OBJECT-TYPE
		SYNTAX	INTEGER {
				qam4(1),
				qam16(2),
				qam32(3),
				qam64(4),
				qam128(5),
				qam256(6)
				}
		MAX-ACCESS	read-write
		STATUS	current
		DESCRIPTION
             "Selects the QAM demodulation type."
		::= { radMM200DemodNVStatus 9 }

	radMM200RxSpectrum OBJECT-TYPE
		SYNTAX	InversionType
		MAX-ACCESS	read-write
		STATUS	current
		DESCRIPTION
             "Inverts the direction of rotation for the demodulation."
		::= { radMM200DemodNVStatus 10 }

	radMM200RxChannelSetting OBJECT-TYPE
		SYNTAX	INTEGER {
				auto(1),
				oneChannel(2),
				twoChannel(3),
				threeChannel(4),
				fourChannel(5)
				}
		MAX-ACCESS	read-write
		STATUS	current
		DESCRIPTION
             "Selects the total number of channels in the MM200.
              Automatic selection allows the MM200 to use the
              maximum number of channels."
		::= { radMM200DemodNVStatus 11 }

	radMM200RxMajorAlarm1Mask OBJECT-TYPE
		SYNTAX	AlarmByteType
		MAX-ACCESS	read-write
		STATUS	current
		DESCRIPTION
             "Major Alarm 1 mask:
              Bit 0 = Glue logic FPGA status
              Bit 1 = Data FPGA status
              Bit 2 = Signal lock detect
              Bit 3 = Sync lock detect
              Bit 4 = Data PLL lock detect
              Bit 5-7 = Spares
              0 = Mask, 1 = Allow"
		::= { radMM200DemodNVStatus 12 }

	radMM200RxMajorAlarm2Mask OBJECT-TYPE
		SYNTAX	AlarmByteType
		MAX-ACCESS	read-write
		STATUS	current
		DESCRIPTION
             "Major Alarm 2 mask:
              Bit 0-7 = Spares
              0 = Mask, 1 = Allow"
		::= { radMM200DemodNVStatus 13 }

	radMM200RxMinorAlarm1Mask OBJECT-TYPE
		SYNTAX	AlarmByteType
		MAX-ACCESS	read-write
		STATUS	current
		DESCRIPTION
             "Minor Alarm 1 mask:
              Bit 0 = Spare
              Bit 1 = Spare
              Bit 2 = Spare
              Bit 3 = Spare
              Bit 4 = Spare
              Bit 5 = Spare
              Bit 6 = Spare
              Bit 7 = Spare
              0 = Mask, 1 = Allow"
		::= { radMM200DemodNVStatus 14 }

	radMM200RxMinorAlarm2Mask OBJECT-TYPE
		SYNTAX	AlarmByteType
		MAX-ACCESS	read-write
		STATUS	current
		DESCRIPTION
             "Minor Alarm 2 mask:
              Bit 0..7 = Spares
              0 = Mask, 1 = Allow"
		::= { radMM200DemodNVStatus 15 }

	radMM200RxAcquisitionControl OBJECT-TYPE
		SYNTAX	INTEGER {
				off(1),
				acquire(2)
				}
		MAX-ACCESS	read-write
		STATUS	current
		DESCRIPTION
				"Enables acquisition and tracking."
		::= { radMM200DemodNVStatus 16 }

	radMM200RxAcquisitionBandwidth OBJECT-TYPE
		SYNTAX	INTEGER (50..400)
		MAX-ACCESS	read-write
		STATUS	current
		DESCRIPTION
				"Sets the +/- acquisition range in KHz, 1 KHz steps."
		::= { radMM200DemodNVStatus 17 }

	radMM200RxAcquisitionDelay OBJECT-TYPE
		SYNTAX	INTEGER (10..255)
		MAX-ACCESS	read-write
		STATUS	current
		DESCRIPTION
				"Sets the time the demodulator remains at frequency before
				trying the next step. Delay is in secs."
		::= { radMM200DemodNVStatus 18 }

	radMM200RxReacquisitionDelay OBJECT-TYPE
		SYNTAX	INTEGER (10..255)
		MAX-ACCESS	read-write
		STATUS	current
		DESCRIPTION
				"Sets the time the demodulator remains at frequency after
				it first looses lock. Delay is in secs."
		::= { radMM200DemodNVStatus 19 }

	radMM200AcquisitionStep OBJECT-TYPE
		SYNTAX	INTEGER (10..100)
		MAX-ACCESS	read-write
		STATUS	current
		DESCRIPTION
				"Sets the frequency step size the demodulator will take when
				trying to acquire. Steps are in KHz."
		::= { radMM200DemodNVStatus 20 }

	radMM200TrackingStep OBJECT-TYPE
		SYNTAX	INTEGER (10..100)
		MAX-ACCESS	read-write
		STATUS	current
		DESCRIPTION
				"Sets the step size the demodulator will use to remove the frequency
				error of a locked signal. Normally set to 10Hz. Steps are in Hz."
		::= { radMM200DemodNVStatus 21 }

-- ---------------------------------------------------------------------------------------------------------------------
-- ---------------------------------------------------------------------------------------------------------------------
-- MM200 demodulator status information.

    radMM200RxMajorAlarm1Status OBJECT-TYPE
       SYNTAX	AlarmByteType
       MAX-ACCESS	read-only
       STATUS	current
       DESCRIPTION
             "Major Alarm 1 status. The agent initializes this to
              the value '00000000'B
              Bit 0 = Glue logic FPGA status
              Bit 1 = Data FPGA status
              Bit 2 = Signal lock detect
              Bit 3 = Sync lock detect
              Bit 4 = Data PLL lock detect
              Bit 5-7 = Spares
              0 = Pass, 1 = Fail"
       ::= { radMM200DemodStatus 1 }

    radMM200RxMajorAlarm2Status OBJECT-TYPE
       SYNTAX	AlarmByteType
       MAX-ACCESS	read-only
       STATUS	current
       DESCRIPTION
             "Major Alarm 2 status. The agent initializes this to
              the value '00000000'B
              Bit 0-7 = Spares
              0 = Pass, 1 = Fail"
       ::= { radMM200DemodStatus 2 }

    radMM200RxMinorAlarm1Status OBJECT-TYPE
       SYNTAX	AlarmByteType
       MAX-ACCESS	read-only
       STATUS	current
       DESCRIPTION
             "Minor Alarm 1 status. The agent initializes this to
              the value '00000000'B
              Bit 0 = Spare
              Bit 1 = Spare
              Bit 2 = Spare
              Bit 3 = Spare
              Bit 4 = Spare
              Bit 5 = Spare
              Bit 6 = Spare
              Bit 7 = Spare
              0 = Pass, 1 = Fail"
       ::= { radMM200DemodStatus 3 }

    radMM200RxMinorAlarm2Status OBJECT-TYPE
       SYNTAX	AlarmByteType
       MAX-ACCESS	read-only
       STATUS	current
       DESCRIPTION
             "Minor Alarm 2 status. The agent initializes this to
              the value '00000000'B
              Bit 0..7 = Spares
              0 = Pass, 1 = Fail"
       ::= { radMM200DemodStatus 4 }

    radMM200RxLatchedMajorAlarm1Status OBJECT-TYPE
       SYNTAX	AlarmByteType
       MAX-ACCESS	read-only
       STATUS	current
       DESCRIPTION
             "A bit field. On startup, the agent initializes this to
              the value '00000000'B.
              Bit 0 = Glue logic FPGA status
              Bit 1 = Data FPGA status
              Bit 2 = Signal lock detect
              Bit 3 = Sync lock detect
              Bit 4 = Data PLL lock detect
              Bit 5-7 = Spares
              0 = Pass, 1 = Fail"
       ::= { radMM200DemodStatus 5 }

    radMM200RxLatchedMajorAlarm2Status OBJECT-TYPE
       SYNTAX	AlarmByteType
       MAX-ACCESS	read-only
       STATUS	current
       DESCRIPTION
             "A bit field. On startup, the agent initializes this to
              the value '00000000'B.
              Bit 0..7 = Spares
              0 = Pass, 1 = Fail"
       ::= { radMM200DemodStatus 6 }

    radMM200RxLatchedMinorAlarm1Status OBJECT-TYPE
       SYNTAX	AlarmByteType
       MAX-ACCESS	read-only
       STATUS	current
       DESCRIPTION
             "A bit field. On startup, the agent initializes this to
              the value '00000000'B.
              Bit 0 = Spare
              Bit 1 = Spare
              Bit 2 = Spare
              Bit 3 = Spare
              Bit 4 = Spare
              Bit 5 = Spare
              Bit 6 = Spare
              Bit 7 = Spare
              0 = Pass, 1 = Fail"
       ::= { radMM200DemodStatus 7 }

    radMM200RxLatchedMinorAlarm2Status OBJECT-TYPE
       SYNTAX	AlarmByteType
       MAX-ACCESS	read-only
       STATUS	current
       DESCRIPTION
             "A bit field. On startup, the agent initializes this to
              the value '00000000'B.
              Bit 0..7 = Spares
              0 = Pass, 1 = Fail"
       ::= { radMM200DemodStatus 8 }

    radMM200RxMaxPayload OBJECT-TYPE
       SYNTAX	INTEGER (0..200000000)
       MAX-ACCESS	read-only
       STATUS	current
       DESCRIPTION
             "Maximum payload at current demodulation."
       ::= { radMM200DemodStatus 9 }

    radMM200RxPercentUtilization OBJECT-TYPE
       SYNTAX	INTEGER (0..65536)
       MAX-ACCESS	read-only
       STATUS	current
       DESCRIPTION
             "% utilization, implied decimal point.
              (i.e. 7985 means 79.85%"
       ::= { radMM200DemodStatus 10 }

    radMM200RxBandwidth OBJECT-TYPE
       SYNTAX	INTEGER (0..40000000)
       MAX-ACCESS	read-only
       STATUS	current
       DESCRIPTION
             "Current bandwidth usage."
       ::= { radMM200DemodStatus 11 }

    radMM200RxInputLevel OBJECT-TYPE
       SYNTAX	INTEGER (-1000..100)
       MAX-ACCESS	read-only
       STATUS	current
       DESCRIPTION
             "Aggregate input level in dBm. Signed implied
              decimal point.
              (i.e. -265 mean -26.5dBm)"
       ::= { radMM200DemodStatus 12 }

-- --------------------------------------------------------------------------------------------------------------------
-- --------------------------------------------------------------------------------------------------------------------
-- MM200 demodulator channel non-volatile status information.

    radMM200RxChannelNVStatusTable OBJECT-TYPE
       SYNTAX	SEQUENCE OF RadMM200RxChannelNVStatusEntry
       MAX-ACCESS	not-accessible
       STATUS	mandatory
       DESCRIPTION
             "MM200 Rx channel non-volatile status Table"
       ::= { mm200MIBObjects 9 }

    radMM200RxChannelNVStatusEntry OBJECT-TYPE
       SYNTAX	RadMM200RxChannelNVStatusEntry
       MAX-ACCESS	not-accessible
       STATUS	current
       DESCRIPTION
             "MM200 Rx channel non-volatile status structure"
       INDEX    { radMM200RxChannelNVIndex }
       ::= { radMM200RxChannelNVStatusTable 1 }

    RadMM200RxChannelNVStatusEntry ::=
       SEQUENCE	{
         radMM200RxChannelNVIndex INTEGER,
         radMM200RxChannelMajorAlarmMask INTEGER,
         radMM200RxChannelMinorAlarmMask INTEGER
       }

    radMM200RxChannelNVIndex OBJECT-TYPE
       SYNTAX	INTEGER (1..4)
       MAX-ACCESS	read-only
       STATUS	current
       DESCRIPTION
             "Index into the MM200 Rx channel non-volatile table."
       ::= { radMM200RxChannelNVStatusEntry 1 }

    radMM200RxChannelMajorAlarmMask OBJECT-TYPE
       SYNTAX	AlarmByteType
       MAX-ACCESS	read-write
       STATUS	current
       DESCRIPTION
             "Major Alarm mask:
              Bit 0 = Demod daughter board FPGA status
              Bit 1 = RF PLL lock detect status
              Bit 2-7 = Spares
              0 = Mask, 1 = Allow"
       ::= { radMM200RxChannelNVStatusEntry 2 }

    radMM200RxChannelMinorAlarmMask OBJECT-TYPE
       SYNTAX	AlarmByteType
       MAX-ACCESS	read-write
       STATUS	current
       DESCRIPTION
             "Minor Alarm mask:
              Bit 0 = QAM lock status
              Bit 1 = FEC lock status
              Bit 2 = FIFO full status
              Bit 3 = FIFO empty status
              Bit 4 = Sync lock status
              Bit 5 = FIFO reload
              Bit 6 = FIFO active
              Bit 7 = Spare
              0 = Mask, 1 = Allow"
       ::= { radMM200RxChannelNVStatusEntry 3 }

-- --------------------------------------------------------------------------------------------------------------------
-- --------------------------------------------------------------------------------------------------------------------
-- MM200 demodulator channel status information.

    radMM200RxChannelStatusTable OBJECT-TYPE
       SYNTAX	SEQUENCE OF RadMM200RxChannelStatusEntry
       MAX-ACCESS	not-accessible
       STATUS	mandatory
       DESCRIPTION
             "MM200 Rx channel volatile status Table"
       ::= { mm200MIBObjects 10 }

    radMM200RxChannelStatusEntry OBJECT-TYPE
       SYNTAX	RadMM200RxChannelStatusEntry
       MAX-ACCESS	not-accessible
       STATUS	current
       DESCRIPTION
             "MM200 Rx channel volatile status structure"
       INDEX	{ radMM200RxChannelIndex }
       ::= { radMM200RxChannelStatusTable 1 }

    RadMM200RxChannelStatusEntry ::=
       SEQUENCE	{
         radMM200RxChannelIndex INTEGER,
         radMM200RxChannelMajorAlarmStatus INTEGER,
         radMM200RxChannelMinorAlarmStatus INTEGER,
         radMM200RxChannelLatchedMajorAlarmStatus INTEGER,
         radMM200RxChannelLatchedMinorAlarmStatus INTEGER,
         radMM200RxChannelBaudRate INTEGER,
         radMM200RxChannelOffsetFrequency INTEGER,
         radMM200RxChannelAGCIntegrator INTEGER,
         radMM200RxChannelSNR INTEGER,
         radMM200RxChannelCBA INTEGER,
         radMM200RxChannelUBA INTEGER,
         radMM200RxChannelInputLevel INTEGER
       }

    radMM200RxChannelIndex OBJECT-TYPE
       SYNTAX	INTEGER (1..4)
       MAX-ACCESS	read-only
       STATUS	current
       DESCRIPTION
             "Index into the MM200 Rx channel volatile table."
       ::= { radMM200RxChannelStatusEntry 1 }

    radMM200RxChannelMajorAlarmStatus OBJECT-TYPE
       SYNTAX	AlarmByteType
       MAX-ACCESS	read-only
       STATUS	current
       DESCRIPTION
             "Major Alarm status:
              Bit 0 = Demod daughter board FPGA status
              Bit 1 = RF PLL lock detect status
              Bit 2-7 = Spares
              0 = PASS, 1 = FAIL"
       ::= { radMM200RxChannelStatusEntry 2 }

    radMM200RxChannelMinorAlarmStatus OBJECT-TYPE
       SYNTAX	AlarmByteType
       MAX-ACCESS	read-only
       STATUS	current
       DESCRIPTION
             "Minor Alarm status:
              Bit 0 = QAM lock status
              Bit 1 = FEC lock status
              Bit 2 = FIFO full status
              Bit 3 = FIFO empty status
              Bit 4 = Sync lock status
              Bit 5 = FIFO reload
              Bit 6 = FIFO active
              Bit 7 = Spare
              0 = PASS, 1 = FAIL"
       ::= { radMM200RxChannelStatusEntry 3 }

    radMM200RxChannelLatchedMajorAlarmStatus OBJECT-TYPE
       SYNTAX	AlarmByteType
       MAX-ACCESS	read-only
       STATUS	current
       DESCRIPTION
             "Major Alarm status:
              Bit 0 = Mod daughter board FPGA status
              Bit 1 = RF PLL lock detect status
              Bit 2-7 = Spares
              0 = PASS, 1 = FAIL"
       ::= { radMM200RxChannelStatusEntry 4 }

    radMM200RxChannelLatchedMinorAlarmStatus OBJECT-TYPE
       SYNTAX	AlarmByteType
       MAX-ACCESS	read-only
       STATUS	current
       DESCRIPTION
             "Minor Alarm status:
              Bit 0 = QAM lock status
              Bit 1 = FEC lock status
              Bit 2 = FIFO full status
              Bit 3 = FIFO empty status
              Bit 4 = Sync lock status
              Bit 5 = FIFO reload
              Bit 6 = FIFO active
              Bit 7 = Spare
              0 = PASS, 1 = FAIL"
       ::= { radMM200RxChannelStatusEntry 5 }

    radMM200RxChannelBaudRate OBJECT-TYPE
       SYNTAX	INTEGER (7000000..200000000)
       MAX-ACCESS	read-only
       STATUS	current
       DESCRIPTION
             "Channel baud rate"
       ::= { radMM200RxChannelStatusEntry 6 }

    radMM200RxChannelOffsetFrequency OBJECT-TYPE
       SYNTAX	INTEGER (-50000..50000)
       MAX-ACCESS	read-only
       STATUS	current
       DESCRIPTION
             "Channel offset frequency in Hz"
       ::= { radMM200RxChannelStatusEntry 7 }


    radMM200RxChannelAGCIntegrator OBJECT-TYPE
       SYNTAX 	INTEGER (0..10000)
       MAX-ACCESS	read-only
       STATUS	current
       DESCRIPTION
             "Channel AGC integrator"
       ::= { radMM200RxChannelStatusEntry 8 }

    radMM200RxChannelSNR OBJECT-TYPE
       SYNTAX	INTEGER (0..100)
       MAX-ACCESS	read-only
       STATUS	current
       DESCRIPTION
             "Channel SNR, signal to noise ratio."
       ::= { radMM200RxChannelStatusEntry 9 }

    radMM200RxChannelCBA OBJECT-TYPE
       SYNTAX	INTEGER (0..65536)
       MAX-ACCESS	read-only
       STATUS	current
       DESCRIPTION
             "Channel CBA, correctable block accumulator."
       ::= { radMM200RxChannelStatusEntry 10 }

    radMM200RxChannelUBA OBJECT-TYPE
       SYNTAX	INTEGER (0..65536)
       MAX-ACCESS	read-only
       STATUS	current
       DESCRIPTION
             "Channel UBA, uncorrectable block accumulator."
       ::= { radMM200RxChannelStatusEntry 11 }

    radMM200RxChannelInputLevel OBJECT-TYPE
       SYNTAX	INTEGER (-1000..100)
       MAX-ACCESS	read-only
       STATUS	current
       DESCRIPTION
             "Channel input level in dBm. Signed implied decimal point
              -265 means -26.5 dBm"
       ::= { radMM200RxChannelStatusEntry 12 }

-- --------------------------------------------------------------------------------------------------------------------
-- --------------------------------------------------------------------------------------------------------------------
-- MM200 demodulator interface non-volatile status information.

    radMM200RxInterfaceNVStatusTable OBJECT-TYPE
       SYNTAX	SEQUENCE OF RadMM200RxInterfaceNVStatusEntry
       MAX-ACCESS	not-accessible
       STATUS	mandatory
       DESCRIPTION
             "MM200 Rx interface non-volatile status Table"
       ::= { mm200MIBObjects 11 }

    radMM200RxInterfaceNVStatusEntry OBJECT-TYPE
       SYNTAX	RadMM200RxInterfaceNVStatusEntry
       MAX-ACCESS	not-accessible
       STATUS	current
       DESCRIPTION
             "MM200 Rx interface non-volatile status structure"
       INDEX	{ radMM200RxInterfaceNVIndex }
       ::= { radMM200RxInterfaceNVStatusTable 1 }

    RadMM200RxInterfaceNVStatusEntry ::=
       SEQUENCE	{
         radMM200RxInterfaceNVIndex INTEGER,
         radMM200RxInterfacePID INTEGER,
         radMM200RxInterfaceDataRate INTEGER,
         radMM200RxInterfaceControl INTEGER,
         radMM200RxInterfaceType INTEGER,
         radMM200RxInterfaceSubType INTEGER,
         radMM200RxInterfaceClockSource INTEGER,
         radMM200RxInterfaceClockFrequency INTEGER,
         radMM200RxInterfaceFraming INTEGER,
         radMM200RxInterfaceVolume INTEGER,
         radMM200RxInterfaceClockPolarity INTEGER,
         radMM200RxInterfaceDataInvert INTEGER,
         radMM200RxInterfaceTerrestrialLoopback INTEGER,
         radMM200RxInterfacePRBS INTEGER,
         radMM200RxInterfaceMajorAlarmMask INTEGER,
         radMM200RxInterfaceMinorAlarmMask INTEGER
       }

    radMM200RxInterfaceNVIndex OBJECT-TYPE
       SYNTAX	INTEGER (1..4)
       MAX-ACCESS	read-only
       STATUS	current
       DESCRIPTION
             "Index into the MM200 Rx interface on-volatile table."
       ::= { radMM200RxInterfaceNVStatusEntry 1 }

    radMM200RxInterfacePID OBJECT-TYPE
       SYNTAX	INTEGER (0..8192)
       MAX-ACCESS	read-write
       STATUS	current
       DESCRIPTION
             "Selects the interface Program Id. If not in 188
              byte framing mode (unframed), this PID steers the
              packet to the appropriate interface. In the MM200,
              only one framed interface is allowed and its packets
              are sent in the clear, without modifications. The
              Null PID and the PIDs of the unframed interfaces should
              be unique. All packets PIDs not equal to these will
              be sent to the framed interface."
       ::= { radMM200RxInterfaceNVStatusEntry 2 }

    radMM200RxInterfaceDataRate OBJECT-TYPE
       SYNTAX	INTEGER (64000..20000000)
       MAX-ACCESS	read-write
       STATUS	current
       DESCRIPTION
             "Selects the data rate in BPS of the individual
              interfaces. The data rate is T3, E3, or STS1
              for G.703
                 155.52M BPS for OC3 and STM1
                 1.544M BPS for T1
                 2.048M BPS for E1
                 Variable for parallel and ASI
                 64K BPS for 8 channel DS0
              The range is between 64K to 200M BPS"
       ::= { radMM200RxInterfaceNVStatusEntry 3 }

    radMM200RxInterfaceControl OBJECT-TYPE
       SYNTAX	ControlType
       MAX-ACCESS	read-write
       STATUS	current
       DESCRIPTION
             "Controls the Rx interface enabling."
       ::= { radMM200RxInterfaceNVStatusEntry 4 }

    radMM200RxInterfaceType OBJECT-TYPE
       SYNTAX	INTEGER {
				asi(1),
				aasi(2),
				t3(3),
				e3(4),
				sts1(5),
				t1(6),
				e1(7),
				ds0x8(8),
				ds0x7A(9),
				parallelDVB(10),
				parallelM2P(11),
				oc3(12),
				stm1(13),
				hssi(14),
				smpt19(15),
				smpt38(16)
		   }
       MAX-ACCESS	read-write
       STATUS	current
       DESCRIPTION
             "Selects the Rx interface type."
       ::= { radMM200RxInterfaceNVStatusEntry 5 }

    radMM200RxInterfaceSubType OBJECT-TYPE
       SYNTAX	INTEGER {
				spare(1),
				}
       MAX-ACCESS	read-write
       STATUS	current
       DESCRIPTION
             "Selects the Rx interface sub-type."
       ::= { radMM200RxInterfaceNVStatusEntry 6 }

    radMM200RxInterfaceClockSource OBJECT-TYPE
       SYNTAX	INTEGER {
				rxclk(1),
				extbnc(2),
				extbal(3),
				internalclk(4)
				}
       MAX-ACCESS	read-write
       STATUS	current
       DESCRIPTION
             "Selects the Rx interface clock source."
       ::= { radMM200RxInterfaceNVStatusEntry 7 }

    radMM200RxInterfaceClockFrequency OBJECT-TYPE
       SYNTAX	INTEGER  {
				mhz2048(1),
				mhz5(2),
				mhz10(3),
				datarate(4)
				}
       MAX-ACCESS	read-write
       STATUS	current
       DESCRIPTION
             "Selects the Rx interface clock frequency."
       ::= { radMM200RxInterfaceNVStatusEntry 8 }

    radMM200RxInterfaceFraming OBJECT-TYPE
       SYNTAX	INTEGER {
				unframed(1),
				mpeg188(2),
				mpeg204(3),
				null188(4),
				null204(3)
				}
       MAX-ACCESS	read-write
       STATUS	current
       DESCRIPTION
             "Selects Unframed (184 Byte proprietary packet),
              MPEG Sync Byte and MPEG Sync Byte plus ReedSolomon."
       ::= { radMM200RxInterfaceNVStatusEntry 9 }

    radMM200RxInterfaceVolume OBJECT-TYPE
       SYNTAX	INTEGER (0..255)
       MAX-ACCESS	read-write
       STATUS		current
       DESCRIPTION
             "Sets the volume on the audio channel on the DS0
              interfaces"
       ::= { radMM200RxInterfaceNVStatusEntry 10 }

    radMM200RxInterfaceClockPolarity OBJECT-TYPE
       SYNTAX	INTEGER {
				normal(1),
				inverted(2),
				}
       MAX-ACCESS	read-write
       STATUS	current
       DESCRIPTION
             "Selects clock polarity for Tx terrestrial clock
             relative to Tx data."
       ::= { radMM200RxInterfaceNVStatusEntry 11 }

    radMM200RxInterfaceDataInvert OBJECT-TYPE
       SYNTAX	InversionType
       MAX-ACCESS	read-write
       STATUS	current
       DESCRIPTION
             "Selects data polarity"
       ::= { radMM200RxInterfaceNVStatusEntry 12 }

    radMM200RxInterfaceTerrestrialLoopback OBJECT-TYPE
       SYNTAX	ControlType
       MAX-ACCESS	read-write
       STATUS	current
       DESCRIPTION
             "Enables or disables Rx Interface Terrestrial Loopback."
       ::= { radMM200RxInterfaceNVStatusEntry 13 }

    radMM200RxInterfacePRBS OBJECT-TYPE
       SYNTAX	INTEGER {
				normal(1),
				prbs23(2),
				prbs23m(3),
				prbs15(4),
				prbs15m(5)
				}
       MAX-ACCESS	read-write
       STATUS	current
       DESCRIPTION
             "Selects the pseudo-random bit sequence for Rx
              interface link testing."
       ::= { radMM200RxInterfaceNVStatusEntry 14 }

    radMM200RxInterfaceMajorAlarmMask OBJECT-TYPE
       SYNTAX	AlarmByteType
       MAX-ACCESS	read-write
       STATUS	current
       DESCRIPTION
             "Major Alarm mask:
              Bit 0 = Interface test
              Bit 1-7 = Spares
              0 = Mask, 1 = Allow"
       ::= { radMM200RxInterfaceNVStatusEntry 15 }

    radMM200RxInterfaceMinorAlarmMask OBJECT-TYPE
       SYNTAX	AlarmByteType
       MAX-ACCESS	read-write
       STATUS	current
       DESCRIPTION
             "Minor Alarm mask:
              Bit 0 = Interface FIFO full
              Bit 1 = Interface FIFO empty
              Bit 2 = Interface PLL lock
              Bit 3 = Interface data activity detect
              Bit 4 = Interface clock activity detect
              Bit 5 = Interface Tx input framing valid, added for AASI
              Bit 6 = Interface signal loss, valid for some interfaces
              Bit 7 = Spare
              0 = Mask, 1 = Allow"
       ::= { radMM200RxInterfaceNVStatusEntry 16 }

-- --------------------------------------------------------------------------------------------------------------------
-- --------------------------------------------------------------------------------------------------------------------
-- MM200 demodulator interface volatile status information.

    radMM200RxInterfaceStatusTable OBJECT-TYPE
       SYNTAX	SEQUENCE OF RadMM200RxInterfaceStatusEntry
       MAX-ACCESS	not-accessible
       STATUS	mandatory
       DESCRIPTION
             "MM200 Rx interface volatile status Table"
       ::= { mm200MIBObjects 12 }

    radMM200RxInterfaceStatusEntry OBJECT-TYPE
       SYNTAX	RadMM200RxInterfaceStatusEntry
       MAX-ACCESS	not-accessible
       STATUS	current
       DESCRIPTION
             "MM200 Rx interface volatile status structure"
       INDEX  { radMM200RxInterfaceIndex }
       ::= { radMM200RxInterfaceStatusTable 1 }

    RadMM200RxInterfaceStatusEntry ::=
       SEQUENCE	{
         radMM200RxInterfaceIndex INTEGER,
         radMM200RxInterfaceMajorAlarmStatus INTEGER,
         radMM200RxInterfaceMinorAlarmStatus INTEGER,
         radMM200RxInterfaceLatchedMajorAlarmStatus INTEGER,
         radMM200RxInterfaceLatchedMinorAlarmStatus INTEGER,
         radMM200RxInterfaceCard INTEGER
       }

    radMM200RxInterfaceIndex OBJECT-TYPE
       SYNTAX	INTEGER (1..4)
       MAX-ACCESS	read-only
       STATUS	current
       DESCRIPTION
             "Index into the MM200 Rx interface volatile table."
       ::= { radMM200RxInterfaceStatusEntry 1 }

    radMM200RxInterfaceMajorAlarmStatus OBJECT-TYPE
       SYNTAX	AlarmByteType
       MAX-ACCESS	read-only
       STATUS	current
       DESCRIPTION
             "Major Alarm status:
              Bit 0 = Interface test
              Bit 1-7 = Spares
              0 = Pass, 1 = Fail"
       ::= { radMM200RxInterfaceStatusEntry 2 }

    radMM200RxInterfaceMinorAlarmStatus OBJECT-TYPE
       SYNTAX	AlarmByteType
       MAX-ACCESS	read-only
       STATUS	current
       DESCRIPTION
             "Minor Alarm status:
              Bit 0 = Interface FIFO full
              Bit 1 = Interface FIFO empty
              Bit 2 = Interface PLL lock
              Bit 3 = Interface data activity detect
              Bit 4 = Interface clock activity detect
              Bit 5 = Interface Tx input framing valid, added for AASI
              Bit 6 = Interface signal loss, valid for some interfaces
              Bit 7 = Spare
              0 = Pass, 1 = Fail"
       ::= { radMM200RxInterfaceStatusEntry 3 }

    radMM200RxInterfaceLatchedMajorAlarmStatus OBJECT-TYPE
       SYNTAX	AlarmByteType
       MAX-ACCESS	read-only
       STATUS	current
       DESCRIPTION
             "Major Alarm status:
              Bit 0 = Interface test
              Bit 1-7 = Spares
              0 = Pass, 1 = Fail"
       ::= { radMM200RxInterfaceStatusEntry 4 }

    radMM200RxInterfaceLatchedMinorAlarmStatus OBJECT-TYPE
       SYNTAX	AlarmByteType
       MAX-ACCESS	read-only
       STATUS	current
       DESCRIPTION
             "Minor Alarm status:
              Bit 0 = Interface FIFO full
              Bit 1 = Interface FIFO empty
              Bit 2 = PLL lock
              Bit 3 = Interface data activity detect
              Bit 4 = Interface clock activity detect
              Bit 5 = Interface Tx input framing valid, added for AASI
              Bit 6 = Interface signal loss, valid for some interfaces
              Bit 7 = Spare
              0 = Pass, 1 = Fail"
       ::= { radMM200RxInterfaceStatusEntry 5 }

	radMM200RxInterfaceCard OBJECT-TYPE
		SYNTAX	INTEGER {
				none(1),
				asi_aasi(2),
				nasi(3),
				t3e3(4),
				t1e1(5),
				ds0(6),
				parallel(7),
				oc3(8),
				hssi(9),
				smpte(10)
            	}
		MAX-ACCESS	read-only
		STATUS	current
		DESCRIPTION
				"Interface card type."
		::= { radMM200RxInterfaceStatusEntry 6 }

-- --------------------------------------------------------------------------------------------------------------------
-- --------------------------------------------------------------------------------------------------------------------
-- MM200 common non-volatile status information.

	radMM200CommonControlMode OBJECT-TYPE
		SYNTAX	INTEGER {
               local(1),
               terminal(2),
               computer(3),
               ethernet(4)
             }
		MAX-ACCESS	read-write
		STATUS	current
		DESCRIPTION
             "Selects Tx control mode."
		::= { radMM200CommonNVStatus 1 }

	radMM200CommonLastRateControl OBJECT-TYPE
		SYNTAX	INTEGER {
               symbol(1),
               data(2),
               auto(3)
             }
		MAX-ACCESS	read-write
		STATUS	current
		DESCRIPTION
             "Selects the last rate control"
		::= { radMM200CommonNVStatus 2 }

	radMM200CommonUserMode OBJECT-TYPE
		SYNTAX	INTEGER {
               debug(1),
               level0(2),
               level1(3),
               level2(4)
             }
		MAX-ACCESS	read-write
		STATUS	current
		DESCRIPTION
             "Selects system user MAX-ACCESS levels"
		::= { radMM200CommonNVStatus 3 }

	radMM200CommonFrequencyPlan OBJECT-TYPE
		SYNTAX	INTEGER {
               auto(1),
               user(2)
             }
		MAX-ACCESS	read-write
		STATUS	current
		DESCRIPTION
             "Selects system frequency plan."
		::= { radMM200CommonNVStatus 4 }

	radMM200CommonAlarm1Mask OBJECT-TYPE
		SYNTAX	AlarmByteType
		MAX-ACCESS	read-write
		STATUS	current
		DESCRIPTION
             "Common Alarm 1 mask:
             Bit 0 = Glue logic FPGA status
             Bit 1 = Test FPGA status
             Bit 2-7 = Spares
             0 = Mask, 1 = Allow"
		::= { radMM200CommonNVStatus 5 }

	radMM200CommonAlarm2Mask OBJECT-TYPE
		SYNTAX	AlarmByteType
		MAX-ACCESS	read-write
		STATUS	current
		DESCRIPTION
             "Common Alarm 2 mask:
              Bit 0..7 = Spares
              0 = Mask, 1 = Allow"
		::= { radMM200CommonNVStatus 6 }

	radMM200CommonResetSNMP OBJECT-TYPE
       SYNTAX	INTEGER (123456789)
       MAX-ACCESS	read-write
       STATUS	current
       DESCRIPTION
             "Forces the SNMP agent to re-initialize and restart."
		::= { radMM200CommonNVStatus 7 }


-- --------------------------------------------------------------------------------------------------------------------
-- --------------------------------------------------------------------------------------------------------------------
-- MM200 common non-volatile status information.

	radMM200CommonAlarm1Status OBJECT-TYPE
		SYNTAX	AlarmByteType
		MAX-ACCESS	read-only
		STATUS	current
		DESCRIPTION
             "A bit field. On startup, the agent initializes this to
              the value '00000000'B
              Bit 0 = Glue logic FPGA status
              Bit 1 = Test FPGA status
              Bit 2-7 = Spares
              0 = Pass, 1 = Fail"
		::= { radMM200CommonStatus 1 }

	radMM200CommonAlarm2Status OBJECT-TYPE
		SYNTAX	AlarmByteType
		MAX-ACCESS	read-only
		STATUS	current
		DESCRIPTION
             "A bit field. On startup, the agent initializes this to
              the value '00000000'B
              Bit 0..7 = Spares
              0 = Pass, 1 = Fail"
		::= { radMM200CommonStatus 2 }

	radMM200CommonLatchedAlarm1Status OBJECT-TYPE
		SYNTAX	AlarmByteType
		MAX-ACCESS	read-only
		STATUS	current
		DESCRIPTION
             "A bit field. On startup, the agent initializes this to
              the value '00000000'B
              Bit 0 = Glue logic FPGA status
              Bit 1 = Test FPGA status
              Bit 2-7 = Spares
              0 = Pass, 1 = Fail"
		::= { radMM200CommonStatus 3 }

	radMM200CommonLatchedAlarm2Status OBJECT-TYPE
		SYNTAX	AlarmByteType
		MAX-ACCESS	read-only
		STATUS	current
		DESCRIPTION
             "A bit field. On startup, the agent initializes this to
              the value '00000000'B
              Bit 0..7 = Spares
              0 = Pass, 1 = Fail"
		::= { radMM200CommonStatus 4 }

-- --------------------------------------------------------------------------------------------------------------------
-- --------------------------------------------------------------------------------------------------------------------


-- MM200 Trap definitions.

-- Include Prefix for compatibility with SNMPv1 traps and procedures
-- employed by multi-lingual and proxy forwarding systems

radMM200MIBTrapPrefix  OBJECT IDENTIFIER ::= { radMM200MIBTraps 0 }

    radMM200ColdStartTrap NOTIFICATION-TYPE
       STATUS	current
       DESCRIPTION
				"Unexpected restart."

       ::= { radMM200MIBTrapPrefix 1 }

    radMM200AuthenticationFailureTrap NOTIFICATION-TYPE
       STATUS	current
       DESCRIPTION
			"Received a message that has failed authentication."
       ::= { radMM200MIBTrapPrefix 2 }

    radMM200ModMajorAlarmTrap NOTIFICATION-TYPE
       STATUS	current
       DESCRIPTION
             "Modulator major alarm trap."
       ::= { radMM200MIBTrapPrefix 3 }

    radMM200ModMinorAlarmTrap NOTIFICATION-TYPE
       STATUS	current
       DESCRIPTION
             "Modulator minor alarm trap."
       ::= { radMM200MIBTrapPrefix 4 }

    radMM200DemodMajorAlarmTrap NOTIFICATION-TYPE
       STATUS	current
       DESCRIPTION
             "Demodulator major alarm trap."
       ::= { radMM200MIBTrapPrefix 5 }

    radMM200DemodMinorAlarmTrap NOTIFICATION-TYPE
       STATUS	current
       DESCRIPTION
             "Demodulator minor alarm trap."
       ::= { radMM200MIBTrapPrefix 6 }

    radMM200CommonAlarmTrap NOTIFICATION-TYPE
       STATUS	current
       DESCRIPTION	"Common alarm trap."
       ::= { radMM200MIBTrapPrefix 7 }

-- --------------------------------------------------------------------------------------------------------------------
-- --------------------------------------------------------------------------------------------------------------------
-- MM200 MIB conformance

    mm200ModNVStatusGroup OBJECT-GROUP
    OBJECTS	{
				radMM200TxCarrierControl,
				radMM200TxTransmitPower,
				radMM200TxIFFrequency,
				radMM200TxIFUser1Frequency,
				radMM200TxIFUser2Frequency,
				radMM200TxIFUser3Frequency,
				radMM200TxIFUser4Frequency,
				radMM200TxIFSeperation,
				radMM200TxDataRate,
				radMM200TxSymbolRate,
				radMM200TxModulation,
				radMM200TxSpectrum,
				radMM200TxCarrierMode,
				radMM200TxChannelSetting,
				radMM200TxMajorAlarm1Mask,
				radMM200TxMajorAlarm2Mask,
				radMM200TxMinorAlarm1Mask,
				radMM200TxMinorAlarm2Mask,
				radMM200TxPRBS
			}
       STATUS	current
       DESCRIPTION	"Modulator non-volatile status group."
       ::= { mm200Groups 1 }

    mm200ModStatusGroup OBJECT-GROUP
    OBJECTS	{
				radMM200TxMajorAlarm1Status,
				radMM200TxMajorAlarm2Status,
				radMM200TxMinorAlarm1Status,
				radMM200TxMinorAlarm2Status,
				radMM200TxLatchedMajorAlarm1Status,
				radMM200TxLatchedMajorAlarm2Status,
				radMM200TxLatchedMinorAlarm1Status,
				radMM200TxLatchedMinorAlarm2Status,
				radMM200TxCarrierStatus,
				radMM200TxMaxPayload,
				radMM200TxPercentUtilization,
				radMM200TxBandwidth
			}
       STATUS	current
       DESCRIPTION	"Modulator volatile status group."
       ::= { mm200Groups 2 }

    mm200ModChannelNVStatusGroup OBJECT-GROUP
		OBJECTS	{
				radMM200TxChannelNVIndex,
				radMM200TxChannelMajorAlarmMask,
				radMM200TxChannelMinorAlarmMask
			}
		STATUS	current
		DESCRIPTION
             "Modulator channel non-volatile status group."
		::= { mm200Groups 3 }

    mm200ModChannelStatusGroup OBJECT-GROUP
		OBJECTS	{
				radMM200TxChannelIndex,
				radMM200TxChannelMajorAlarmStatus,
				radMM200TxChannelMinorAlarmStatus,
				radMM200TxChannelLatchedMajorAlarmStatus,
				radMM200TxChannelLatchedMinorAlarmStatus,
				radMM200TxChannelBaudRate,
				radMM200TxChannelBaudState
			}
		STATUS	current
		DESCRIPTION	"Modulator channel volatile status group."
		::= { mm200Groups 4 }

    mm200ModInterfaceNVStatusGroup OBJECT-GROUP
		OBJECTS	{
				radMM200TxInterfaceNVIndex,
				radMM200TxInterfacePID,
				radMM200TxInterfaceDataRate,
				radMM200TxInterfaceControl,
				radMM200TxInterfaceType,
				radMM200TxInterfaceSubType,
				radMM200TxInterfaceFraming,
				radMM200TxInterfaceVolume,
				radMM200TxInterfaceClockPolarity,
				radMM200TxInterfaceDataInvert,
				radMM200TxInterfaceBasebandLoopback,
				radMM200TxInterfacePRBS,
				radMM200TxInterfaceMajorAlarmMask,
				radMM200TxInterfaceMinorAlarmMask
			}
		STATUS	current
		DESCRIPTION	"Modulator interface non-volatile status group."
		::= { mm200Groups 5 }

    mm200ModInterfaceStatusGroup OBJECT-GROUP
		OBJECTS	{
				radMM200TxInterfaceIndex,
				radMM200TxInterfaceMajorAlarmStatus,
				radMM200TxInterfaceMinorAlarmStatus,
				radMM200TxInterfaceLatchedMajorAlarmStatus,
				radMM200TxInterfaceLatchedMinorAlarmStatus
			}
		STATUS	current
		DESCRIPTION	"Modulator interface volatile status group."
		::= { mm200Groups 6 }

    mm200DemodNVStatusGroup OBJECT-GROUP
		OBJECTS	{
				radMM200RxIFFrequency,
				radMM200RxIFUser1Frequency,
				radMM200RxIFUser2Frequency,
				radMM200RxIFUser3Frequency,
				radMM200RxIFUser4Frequency,
				radMM200RxIFSeperation,
				radMM200RxDataRate,
				radMM200RxSymbolRate,
				radMM200RxDemodulation,
				radMM200RxSpectrum,
				radMM200RxChannelSetting,
				radMM200RxMajorAlarm1Mask,
				radMM200RxMajorAlarm2Mask,
				radMM200RxMinorAlarm1Mask,
				radMM200RxMinorAlarm2Mask
			}
		STATUS	current
		DESCRIPTION	"Demodulator non-volatile status group."
		::= { mm200Groups 7 }

    mm200DemodStatusGroup OBJECT-GROUP
		OBJECTS	{
				radMM200RxMajorAlarm1Status,
				radMM200RxMajorAlarm2Status,
				radMM200RxMinorAlarm1Status,
				radMM200RxMinorAlarm2Status,
				radMM200RxLatchedMajorAlarm1Status,
				radMM200RxLatchedMajorAlarm2Status,
				radMM200RxLatchedMinorAlarm1Status,
				radMM200RxLatchedMinorAlarm2Status,
				radMM200RxMaxPayload,
				radMM200RxPercentUtilization,
				radMM200RxBandwidth,
				radMM200RxInputLevel
			}
		STATUS	current
		DESCRIPTION	"Demodulator volatile status group."
		::= { mm200Groups 8 }

    mm200DemodChannelNVStatusGroup OBJECT-GROUP
		OBJECTS	{
				radMM200RxChannelNVIndex,
				radMM200RxChannelMajorAlarmMask,
				radMM200RxChannelMinorAlarmMask
			}
		STATUS	current
		DESCRIPTION	"Demodulator channel non-volatile status group."
		::= { mm200Groups 9 }

    mm200DemodChannelStatusGroup OBJECT-GROUP
		OBJECTS	{
				radMM200RxChannelIndex,
				radMM200RxChannelMajorAlarmStatus,
				radMM200RxChannelMinorAlarmStatus,
				radMM200RxChannelLatchedMajorAlarmStatus,
				radMM200RxChannelLatchedMinorAlarmStatus,
				radMM200RxChannelBaudRate,
				radMM200RxChannelOffsetFrequency,
				radMM200RxChannelAGCIntegrator,
				radMM200RxChannelSNR,
				radMM200RxChannelCBA,
				radMM200RxChannelUBA,
				radMM200RxChannelInputLevel
			}
		STATUS	current
		DESCRIPTION	"Demodulator channel volatile status group."
		::= { mm200Groups 10 }

    mm200DemodInterfaceNVStatusGroup OBJECT-GROUP
    OBJECTS	{
				radMM200RxInterfaceNVIndex,
				radMM200RxInterfacePID,
				radMM200RxInterfaceDataRate,
				radMM200RxInterfaceControl,
				radMM200RxInterfaceType,
				radMM200RxInterfaceSubType,
				radMM200RxInterfaceClockSource,
				radMM200RxInterfaceClockFrequency,
				radMM200RxInterfaceFraming,
				radMM200RxInterfaceVolume,
				radMM200RxInterfaceClockPolarity,
				radMM200RxInterfaceDataInvert,
				radMM200RxInterfaceTerrestrialLoopback,
				radMM200RxInterfacePRBS,
				radMM200RxInterfaceMajorAlarmMask,
				radMM200RxInterfaceMinorAlarmMask
			}
		STATUS	current
		DESCRIPTION	"Demodulator interface non-volatile status group."
		::= { mm200Groups 11 }

    mm200DemodInterfaceStatusGroup OBJECT-GROUP
		OBJECTS	{
				radMM200RxInterfaceIndex,
				radMM200RxInterfaceMajorAlarmStatus,
				radMM200RxInterfaceMinorAlarmStatus,
				radMM200RxInterfaceLatchedMajorAlarmStatus,
				radMM200RxInterfaceLatchedMinorAlarmStatus
			}
		STATUS	current
		DESCRIPTION	"Demodulator interface volatile status group."
		::= { mm200Groups 12 }

    mm200CommonNVStatusGroup OBJECT-GROUP
		OBJECTS	{
				radMM200CommonControlMode,
				radMM200CommonLastRateControl,
				radMM200CommonUserMode,
				radMM200CommonFrequencyPlan,
				radMM200CommonAlarm1Mask,
				radMM200CommonAlarm2Mask,
				radMM200CommonResetSNMP
			}
		STATUS	current
		DESCRIPTION	"Common non-volatile status group."
		::= { mm200Groups 13 }

    mm200CommonStatusGroup OBJECT-GROUP
		OBJECTS	{
				radMM200CommonAlarm1Status,
				radMM200CommonAlarm2Status,
				radMM200CommonLatchedAlarm1Status,
				radMM200CommonLatchedAlarm2Status
			}
		STATUS	current
		DESCRIPTION	"Common volatile status group."
		::= { mm200Groups 14 }


    mm200CommonNotificationsGroup NOTIFICATION-GROUP
		NOTIFICATIONS {
				radMM200ColdStartTrap,
				radMM200AuthenticationFailureTrap
			}
		STATUS	current
		DESCRIPTION
				"The two notifications which an SNMPv2 entity is required to
				implement."
		::= { mm200Groups 15 }

    mm200ModNotificationsGroup NOTIFICATION-GROUP
		NOTIFICATIONS  {
				radMM200ModMajorAlarmTrap,
				radMM200ModMinorAlarmTrap,
				radMM200CommonAlarmTrap
			}
		STATUS	current
		DESCRIPTION  "Modulator traps group."
		::= { mm200Groups 16 }

    mm200DemodNotificationsGroup NOTIFICATION-GROUP
		NOTIFICATIONS   {
				radMM200DemodMajorAlarmTrap,
				radMM200DemodMinorAlarmTrap,
				radMM200CommonAlarmTrap
			}
		STATUS	current
		DESCRIPTION  "Demodulator traps group."
		::= { mm200Groups 17 }

END
