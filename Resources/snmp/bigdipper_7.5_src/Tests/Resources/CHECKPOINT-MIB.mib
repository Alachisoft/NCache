CHECKPOINT-MIB DEFINITIONS ::= BEGIN

	 -- SUBTREE: 1.3.6.1.4.1.2620.1
	 -- iso.org.dod.internet.private.enterprises.checkpoint.products

     IMPORTS
         enterprises
           FROM RFC1155-SMI
		TRAP-TYPE
			FROM RFC-1215
         OBJECT-TYPE
             FROM RFC-1212;

     -- textual conventions

     DisplayString ::=
       OCTET STRING
     -- This data type is used to model textual information taken
     -- from the NVT ASCII character set. By convention, objects
     -- with this syntax are declared as having
     --
     --   SIZE (0..255)


	checkpoint	OBJECT IDENTIFIER ::= { enterprises 2620 }
	products	OBJECT IDENTIFIER ::= { checkpoint 1 }
	fw		OBJECT IDENTIFIER ::= { products 1 }
	vpn		OBJECT IDENTIFIER ::= { products 2 }
	fg		OBJECT IDENTIFIER ::= { products 3 }
	ha		OBJECT IDENTIFIER ::= { products 5 }
	svn     	OBJECT IDENTIFIER ::= { products 6 }
	mngmt	  	OBJECT IDENTIFIER ::= { products 7 }
	wam       OBJECT IDENTIFIER ::= { products 8 }
	dtps      OBJECT IDENTIFIER ::= { products 9 }
	ls       OBJECT IDENTIFIER ::= { products 11 }


	 -- the FW group
	 -- Overall statistics and state


	 fwPolicyStat OBJECT IDENTIFIER ::= { fw 25 }
   fwPerfStat  OBJECT IDENTIFIER ::= { fw 26 }

	 fwHmem   OBJECT IDENTIFIER ::= { fwPerfStat 1 }
	 fwKmem   OBJECT IDENTIFIER ::= { fwPerfStat 2 }
	 fwInspect  OBJECT IDENTIFIER ::= { fwPerfStat 3 }
	 fwCookies  OBJECT IDENTIFIER ::= { fwPerfStat 4 }
	 fwChains  OBJECT IDENTIFIER ::= { fwPerfStat 5 }
	 fwFragments OBJECT IDENTIFIER ::= { fwPerfStat 6 }
	 fwUfp    OBJECT IDENTIFIER ::= { fwPerfStat 8 }
	 fwSS    OBJECT IDENTIFIER ::= { fwPerfStat 9 }
	 fwSS-http  OBJECT IDENTIFIER ::= { fwSS 1 }
	 fwSS-ftp  OBJECT IDENTIFIER ::= { fwSS 2 }
	 fwSS-telnet OBJECT IDENTIFIER ::= { fwSS 3 }
	 fwSS-rlogin OBJECT IDENTIFIER ::= { fwSS 4 }
	 fwSS-ufp  OBJECT IDENTIFIER ::= { fwSS 5 }
	 fwSS-smtp  OBJECT IDENTIFIER ::= { fwSS 6 }

	 fwModuleState OBJECT-TYPE
       SYNTAX DisplayString (SIZE (0..255))
       ACCESS read-only
       STATUS mandatory
       DESCRIPTION
           "The state of the fw module"
       ::= { fw 1 }

	 fwFilterName OBJECT-TYPE
       SYNTAX DisplayString (SIZE (0..255))
       ACCESS read-only
       STATUS mandatory
       DESCRIPTION
           "The name of the loaded filter"
       ::= { fw 2 }

	 fwFilterDate OBJECT-TYPE
       SYNTAX DisplayString (SIZE (0..255))
       ACCESS read-only
       STATUS mandatory
       DESCRIPTION
           "Install time"
       ::= { fw 3 }

	 fwAccepted OBJECT-TYPE
       SYNTAX INTEGER
       ACCESS read-only
       STATUS mandatory
       DESCRIPTION
           "The number of accepted packets."
       ::= { fw 4 }

	 fwRejected OBJECT-TYPE
       SYNTAX INTEGER
       ACCESS read-only
       STATUS mandatory
       DESCRIPTION
           "The number of rejected packets."
       ::= { fw 5 }

	 fwDropped OBJECT-TYPE
       SYNTAX INTEGER
       ACCESS read-only
       STATUS mandatory
       DESCRIPTION
           "The number of dropped packets."
       ::= { fw 6 }

	 fwLogged OBJECT-TYPE
       SYNTAX INTEGER
       ACCESS read-only
       STATUS mandatory
       DESCRIPTION
           "The number of logged packets."
       ::= { fw 7 }

	 fwMajor OBJECT-TYPE
       SYNTAX INTEGER
       ACCESS read-only
       STATUS mandatory
       DESCRIPTION
           "Major version"
       ::= { fw 8 }

	 fwMinor OBJECT-TYPE
       SYNTAX INTEGER
       ACCESS read-only
       STATUS mandatory
       DESCRIPTION
           "Minor version"
       ::= { fw 9 }

	 fwProduct OBJECT-TYPE
       SYNTAX DisplayString (SIZE (0..255))
       ACCESS read-only
       STATUS mandatory
       DESCRIPTION
           "Product name"
       ::= { fw 10 }

	 fwEvent OBJECT-TYPE
       SYNTAX DisplayString (SIZE (0..255))
       ACCESS read-only
       STATUS mandatory
       DESCRIPTION
           "A string containing the last snmp trap sent via fw"
       ::= { fw 11 }

   fwProdName OBJECT-TYPE
       SYNTAX DisplayString (SIZE (0..255))
       ACCESS read-only
       STATUS mandatory
       DESCRIPTION
           "Product name"
       ::= { fw 21 }

	 fwVerMajor OBJECT-TYPE
       SYNTAX INTEGER
       ACCESS read-only
       STATUS mandatory
       DESCRIPTION
           "Major version"
       ::= { fw 22 }

	 fwVerMinor OBJECT-TYPE
       SYNTAX INTEGER
       ACCESS read-only
       STATUS mandatory
       DESCRIPTION
           "Minor version"
       ::= { fw 23 }

	 fwKernelBuild OBJECT-TYPE
       SYNTAX INTEGER
       ACCESS read-only
       STATUS mandatory
       DESCRIPTION
           "Kernel build num"
       ::= { fw 24 }

	 fwPolicyName OBJECT-TYPE
	 		 SYNTAX DisplayString (SIZE (0..255))
	 		 ACCESS read-only
	 		 STATUS mandatory
	 		 DESCRIPTION
	 		     "Policy Name"
	 		 ::= { fwPolicyStat 1 }

	 fwInstallTime OBJECT-TYPE
	 		 SYNTAX DisplayString (SIZE (0..255))
	 		 ACCESS read-only
	 		 STATUS mandatory
	 		 DESCRIPTION
	 		     "Policy install time"
	 		 ::= { fwPolicyStat 2 }
   fwNumConn OBJECT-TYPE
	 		 SYNTAX INTEGER
	 		 ACCESS read-only
	 		 STATUS mandatory
	 		 DESCRIPTION
	 		     "Number of connections"
	 		 ::= { fwPolicyStat 3 }

	 fwPeakNumConn OBJECT-TYPE
	 		 SYNTAX INTEGER
	 		 ACCESS read-only
	 		 STATUS mandatory
	 		 DESCRIPTION
	 		     "Peak number of connections"
	 		 ::= { fwPolicyStat 4 }

	 fwIfTable OBJECT-TYPE
	     SYNTAX SEQUENCE OF FwIfEntry
			 ACCESS not-accessible
			 STATUS mandatory
			  ::= { fwPolicyStat 5 }


	 fwIfEntry OBJECT-TYPE
	     SYNTAX FwIfEntry
	     ACCESS not-accessible
	     STATUS mandatory
	     ::= { fwIfTable 1 }

   FwIfEntry ::=
       SEQUENCE {
         fwIfIndex
           INTEGER,
         fwIfName
           DisplayString,
         fwAcceptPcktsIn
           INTEGER,
         fwAcceptPcktsOut
           INTEGER,
         fwAcceptBytesIn
           INTEGER,
         fwAcceptBytesOut
           INTEGER,
         fwDropPcktsIn
				   INTEGER,
   		   fwDropPcktsOut
   		     INTEGER,
         fwRejectPcktsIn
				   INTEGER,
				 fwRejectPcktsOut
				   INTEGER,
				 fwLogIn
				   INTEGER,
				 fwLogOut
           INTEGER
       }

   fwIfIndex OBJECT-TYPE
      SYNTAX INTEGER
      ACCESS read-only
      STATUS mandatory
      ::= { fwIfEntry 1 }

   fwIfName OBJECT-TYPE
      SYNTAX DisplayString
      ACCESS read-only
      STATUS mandatory
      ::= { fwIfEntry 2 }

   fwAcceptPcktsIn OBJECT-TYPE
      SYNTAX INTEGER
      ACCESS read-only
      STATUS mandatory
      ::= { fwIfEntry 5 }

   fwAcceptPcktsOut OBJECT-TYPE
      SYNTAX INTEGER
      ACCESS read-only
      STATUS mandatory
      ::= { fwIfEntry 6 }

	 fwAcceptBytesIn OBJECT-TYPE
      SYNTAX INTEGER
      ACCESS read-only
      STATUS mandatory
      ::= { fwIfEntry 7 }

	 fwAcceptBytesOut OBJECT-TYPE
      SYNTAX INTEGER
      ACCESS read-only
      STATUS mandatory
      ::= { fwIfEntry 8 }


   fwDropPcktsIn OBJECT-TYPE
      SYNTAX INTEGER
      ACCESS read-only
      STATUS mandatory
      ::= { fwIfEntry 9 }

   fwDropPcktsOut OBJECT-TYPE
      SYNTAX INTEGER
      ACCESS read-only
      STATUS mandatory
      ::= { fwIfEntry 10 }


   fwRejectPcktsIn OBJECT-TYPE
      SYNTAX INTEGER
      ACCESS read-only
      STATUS mandatory
      ::= { fwIfEntry 11 }

   fwRejectPcktsOut OBJECT-TYPE
      SYNTAX INTEGER
      ACCESS read-only
      STATUS mandatory
      ::= { fwIfEntry 12 }

   fwLogIn OBJECT-TYPE
      SYNTAX INTEGER
      ACCESS read-only
      STATUS mandatory
      ::= { fwIfEntry 13 }

   fwLogOut OBJECT-TYPE
      SYNTAX INTEGER
      ACCESS read-only
      STATUS mandatory
      ::= { fwIfEntry 14 }


	 fwHmem-block-size	 OBJECT-TYPE
      SYNTAX INTEGER
      ACCESS read-only
      STATUS mandatory
      DESCRIPTION
	 		    "hmem - block size"
      ::= { fwHmem 1 }

	 fwHmem-requested-bytes OBJECT-TYPE
      SYNTAX INTEGER
      ACCESS read-only
      STATUS mandatory
      DESCRIPTION
	 		    "hmem - requested bytes"
      ::= { fwHmem 2 }

	 fwHmem-initial-allocated-bytes OBJECT-TYPE
      SYNTAX INTEGER
      ACCESS read-only
      STATUS mandatory
      DESCRIPTION
	 		    "hmem - initial allocated bytes"
      ::= { fwHmem 3 }

	 fwHmem-initial-allocated-blocks OBJECT-TYPE
      SYNTAX INTEGER
      ACCESS read-only
      STATUS mandatory
      DESCRIPTION
	 		    "hmem - initial allocated blocks"
      ::= { fwHmem 4 }

	 fwHmem-initial-allocated-pools OBJECT-TYPE
      SYNTAX INTEGER
      ACCESS read-only
      STATUS mandatory
      DESCRIPTION
	 		    "hmem - initial allocated pools"
      ::= { fwHmem 5 }

	 fwHmem-current-allocated-bytes OBJECT-TYPE
      SYNTAX INTEGER
      ACCESS read-only
      STATUS mandatory
      DESCRIPTION
	 		    "hmem - current allocated bytes"
      ::= { fwHmem 6 }

	 fwHmem-current-allocated-blocks OBJECT-TYPE
      SYNTAX INTEGER
      ACCESS read-only
      STATUS mandatory
      DESCRIPTION
	 		    "hmem - current allocated blocks"
      ::= { fwHmem 7 }

	 fwHmem-current-allocated-pools OBJECT-TYPE
      SYNTAX INTEGER
      ACCESS read-only
      STATUS mandatory
      DESCRIPTION
	 		    "hmem - current allocated pools"
      ::= { fwHmem 8 }

	 fwHmem-maximum-bytes OBJECT-TYPE
      SYNTAX INTEGER
      ACCESS read-only
      STATUS mandatory
      DESCRIPTION
	 		    "hmem - maximum bytes"
      ::= { fwHmem 9 }

	 fwHmem-maximum-pools OBJECT-TYPE
      SYNTAX INTEGER
      ACCESS read-only
      STATUS mandatory
      DESCRIPTION
	 		    "hmem - maximum pools"
      ::= { fwHmem 10 }

	 fwHmem-bytes-used OBJECT-TYPE
      SYNTAX INTEGER
      ACCESS read-only
      STATUS mandatory
      DESCRIPTION
	 		    "hmem - bytes used"
      ::= { fwHmem 11 }

	 fwHmem-blocks-used OBJECT-TYPE
      SYNTAX INTEGER
      ACCESS read-only
      STATUS mandatory
      DESCRIPTION
	 		    "hmem - blocks used"
      ::= { fwHmem 12 }

	 fwHmem-bytes-unused OBJECT-TYPE
      SYNTAX INTEGER
      ACCESS read-only
      STATUS mandatory
      DESCRIPTION
	 		    "hmem - bytes unused"
      ::= { fwHmem 13 }

	 fwHmem-blocks-unused OBJECT-TYPE
      SYNTAX INTEGER
      ACCESS read-only
      STATUS mandatory
      DESCRIPTION
	 		    "hmem - blocks unused"
      ::= { fwHmem 14 }

	 fwHmem-bytes-peak OBJECT-TYPE
      SYNTAX INTEGER
      ACCESS read-only
      STATUS mandatory
      DESCRIPTION
	 		    "hmem - bytes peak"
      ::= { fwHmem 15 }

	 fwHmem-blocks-peak OBJECT-TYPE
      SYNTAX INTEGER
      ACCESS read-only
      STATUS mandatory
      DESCRIPTION
	 		    "hmem - blocks peak"
      ::= { fwHmem 16 }

	 fwHmem-bytes-internal-use OBJECT-TYPE
      SYNTAX INTEGER
      ACCESS read-only
      STATUS mandatory
      DESCRIPTION
	 		    "hmem - bytes internal use"
      ::= { fwHmem 17 }

	 fwHmem-number-of-items OBJECT-TYPE
      SYNTAX INTEGER
      ACCESS read-only
      STATUS mandatory
      DESCRIPTION
	 		    "hmem - number of items"
      ::= { fwHmem 18 }

	 fwHmem-alloc-operations OBJECT-TYPE
      SYNTAX INTEGER
      ACCESS read-only
      STATUS mandatory
      DESCRIPTION
	 		    "hmem - alloc operations"
      ::= { fwHmem 19 }

	 fwHmem-free-operations OBJECT-TYPE
      SYNTAX INTEGER
      ACCESS read-only
      STATUS mandatory
      DESCRIPTION
	 		    "hmem - free operations"
      ::= { fwHmem 20 }

	 fwHmem-failed-alloc OBJECT-TYPE
      SYNTAX INTEGER
      ACCESS read-only
      STATUS mandatory
      DESCRIPTION
	 		    "hmem - failed alloc"
      ::= { fwHmem 21 }

	 fwHmem-failed-free OBJECT-TYPE
      SYNTAX INTEGER
      ACCESS read-only
      STATUS mandatory
      DESCRIPTION
	 		    "hmem - failed free"
      ::= { fwHmem 22 }


	 fwKmem-system-physical-mem OBJECT-TYPE
      SYNTAX INTEGER
      ACCESS read-only
      STATUS mandatory
      DESCRIPTION
	 		    "kmem - system physical mem"
      ::= { fwKmem 1 }

	 fwKmem-available-physical-mem OBJECT-TYPE
      SYNTAX INTEGER
      ACCESS read-only
      STATUS mandatory
      DESCRIPTION
	 		    "kmem - available physical mem"
      ::= { fwKmem 2 }

	 fwKmem-aix-heap-size OBJECT-TYPE
      SYNTAX INTEGER
      ACCESS read-only
      STATUS mandatory
      DESCRIPTION
	 		    "kmem - aix heap size"
      ::= { fwKmem 3 }

	 fwKmem-bytes-used OBJECT-TYPE
      SYNTAX INTEGER
      ACCESS read-only
      STATUS mandatory
      DESCRIPTION
	 		    "kmem - bytes used"
      ::= { fwKmem 4 }

	 fwKmem-blocking-bytes-used OBJECT-TYPE
      SYNTAX INTEGER
      ACCESS read-only
      STATUS mandatory
      DESCRIPTION
	 		    "kmem - blocking bytes used"
      ::= { fwKmem 5 }

	 fwKmem-non-blocking-bytes-used OBJECT-TYPE
      SYNTAX INTEGER
      ACCESS read-only
      STATUS mandatory
      DESCRIPTION
	 		    "kmem - non blocking bytes used"
      ::= { fwKmem 6 }

	 fwKmem-bytes-unused OBJECT-TYPE
      SYNTAX INTEGER
      ACCESS read-only
      STATUS mandatory
      DESCRIPTION
	 		    "kmem - bytes unused"
      ::= { fwKmem 7 }

	 fwKmem-bytes-peak OBJECT-TYPE
      SYNTAX INTEGER
      ACCESS read-only
      STATUS mandatory
      DESCRIPTION
	 		    "kmem - bytes peak"
      ::= { fwKmem 8 }

	 fwKmem-blocking-bytes-peak OBJECT-TYPE
      SYNTAX INTEGER
      ACCESS read-only
      STATUS mandatory
      DESCRIPTION
	 		    "kmem - blocking bytes peak"
      ::= { fwKmem 9 }

	 fwKmem-non-blocking-bytes-peak OBJECT-TYPE
      SYNTAX INTEGER
      ACCESS read-only
      STATUS mandatory
      DESCRIPTION
	 		    "kmem - non blocking bytes peak"
      ::= { fwKmem 10 }

	 fwKmem-bytes-internal-use OBJECT-TYPE
      SYNTAX INTEGER
      ACCESS read-only
      STATUS mandatory
      DESCRIPTION
	 		    "kmem - bytes internal use"
      ::= { fwKmem 11 }

	 fwKmem-number-of-items OBJECT-TYPE
      SYNTAX INTEGER
      ACCESS read-only
      STATUS mandatory
      DESCRIPTION
	 		    "kmem - number of items"
      ::= { fwKmem 12 }

	 fwKmem-alloc-operations OBJECT-TYPE
      SYNTAX INTEGER
      ACCESS read-only
      STATUS mandatory
      DESCRIPTION
	 		    "kmem - alloc operations"
      ::= { fwKmem 13 }

	 fwKmem-free-operations OBJECT-TYPE
      SYNTAX INTEGER
      ACCESS read-only
      STATUS mandatory
      DESCRIPTION
	 		    "kmem - free operations"
      ::= { fwKmem 14 }

	 fwKmem-failed-alloc OBJECT-TYPE
      SYNTAX INTEGER
      ACCESS read-only
      STATUS mandatory
      DESCRIPTION
	 		    "kmem - failed alloc"
      ::= { fwKmem 15 }

	 fwKmem-failed-free OBJECT-TYPE
      SYNTAX INTEGER
      ACCESS read-only
      STATUS mandatory
      DESCRIPTION
	 		    "kmem - failed free"
      ::= { fwKmem 16 }

	 fwInspect-packets OBJECT-TYPE
      SYNTAX INTEGER
      ACCESS read-only
      STATUS mandatory
      DESCRIPTION
	 		    "inspect - packets"
      ::= { fwInspect 1 }

	 fwInspect-operations OBJECT-TYPE
      SYNTAX INTEGER
      ACCESS read-only
      STATUS mandatory
      DESCRIPTION
	 		    "inspect - operations"
      ::= { fwInspect 2 }

	 fwInspect-lookups OBJECT-TYPE
      SYNTAX INTEGER
      ACCESS read-only
      STATUS mandatory
      DESCRIPTION
	 		    "inspect - lookups"
      ::= { fwInspect 3 }

	 fwInspect-record OBJECT-TYPE
      SYNTAX INTEGER
      ACCESS read-only
      STATUS mandatory
      DESCRIPTION
	 		    "inspect - record"
      ::= { fwInspect 4 }

	 fwInspect-extract OBJECT-TYPE
      SYNTAX INTEGER
      ACCESS read-only
      STATUS mandatory
      DESCRIPTION
	 		    "inspect - extract"
      ::= { fwInspect 5 }

   fwCookies-total OBJECT-TYPE
      SYNTAX INTEGER
      ACCESS read-only
      STATUS mandatory
      DESCRIPTION
	 		    "cookies - total"
      ::= { fwCookies 1 }

	 fwCookies-allocfwCookies-total OBJECT-TYPE
      SYNTAX INTEGER
      ACCESS read-only
      STATUS mandatory
      DESCRIPTION
	 		    "cookies - alloc"
      ::= { fwCookies 2 }

	 fwCookies-freefwCookies-total OBJECT-TYPE
      SYNTAX INTEGER
      ACCESS read-only
      STATUS mandatory
      DESCRIPTION
	 		    "cookies - free"
      ::= { fwCookies 3 }

	 fwCookies-dupfwCookies-total OBJECT-TYPE
      SYNTAX INTEGER
      ACCESS read-only
      STATUS mandatory
      DESCRIPTION
	 		    "cookies - dup"
      ::= { fwCookies 4 }

	 fwCookies-getfwCookies-total OBJECT-TYPE
      SYNTAX INTEGER
      ACCESS read-only
      STATUS mandatory
      DESCRIPTION
	 		    "cookies - get"
      ::= { fwCookies 5 }

	 fwCookies-putfwCookies-total OBJECT-TYPE
      SYNTAX INTEGER
      ACCESS read-only
      STATUS mandatory
      DESCRIPTION
	 		    "cookies - put"
      ::= { fwCookies 6 }

	 fwCookies-lenfwCookies-total OBJECT-TYPE
      SYNTAX INTEGER
      ACCESS read-only
      STATUS mandatory
      DESCRIPTION
	 		    "cookies - len"
      ::= { fwCookies 7 }

	 fwChains-alloc OBJECT-TYPE
      SYNTAX INTEGER
      ACCESS read-only
      STATUS mandatory
      DESCRIPTION
	 		    "chains - alloc"
      ::= { fwChains 1 }

   fwChains-free OBJECT-TYPE
      SYNTAX INTEGER
      ACCESS read-only
      STATUS mandatory
      DESCRIPTION
	 		    "chains - free"
      ::= { fwChains 2 }

   fwFrag-fragments OBJECT-TYPE
      SYNTAX INTEGER
      ACCESS read-only
      STATUS mandatory
      DESCRIPTION
	 		    "fragments - fragments"
      ::= { fwFragments 1 }

   fwFrag-expired OBJECT-TYPE
      SYNTAX INTEGER
      ACCESS read-only
      STATUS mandatory
      DESCRIPTION
	 		    "fragments - expired"
      ::= { fwFragments 2 }

   fwFrag-packets OBJECT-TYPE
      SYNTAX INTEGER
      ACCESS read-only
      STATUS mandatory
      DESCRIPTION
	 		    "fragments - packets"
      ::= { fwFragments 3 }

   fwUfpHitRatio OBJECT-TYPE
      SYNTAX INTEGER
      ACCESS read-only
      STATUS mandatory
      DESCRIPTION
	 		    "ufp - % hits ratio"
      ::= { fwUfp 1 }

   fwUfpInspected OBJECT-TYPE
      SYNTAX INTEGER
      ACCESS read-only
      STATUS mandatory
      DESCRIPTION
	 		    "ufp - total connections"
      ::= { fwUfp 2 }

   fwUfpHits OBJECT-TYPE
      SYNTAX INTEGER
      ACCESS read-only
      STATUS mandatory
      DESCRIPTION
	 		    "ufp - hits connections"
      ::= { fwUfp 3 }

   fwSS-http-pid OBJECT-TYPE
      SYNTAX INTEGER
      ACCESS read-only
      STATUS mandatory
      DESCRIPTION
	 		    "http - pid"
      ::= { fwSS-http 1 }

   fwSS-http-proto OBJECT-TYPE
      SYNTAX INTEGER
      ACCESS read-only
      STATUS mandatory
      DESCRIPTION
	 		    "http - proto"
      ::= { fwSS-http 2 }

   fwSS-http-port OBJECT-TYPE
      SYNTAX INTEGER
      ACCESS read-only
      STATUS mandatory
      DESCRIPTION
	 		    "http - port"
      ::= { fwSS-http 3 }

   fwSS-http-logical-port OBJECT-TYPE
      SYNTAX INTEGER
      ACCESS read-only
      STATUS mandatory
      DESCRIPTION
	 		    "http - logical port"
      ::= { fwSS-http 4 }

   fwSS-http-max-avail-socket OBJECT-TYPE
      SYNTAX INTEGER
      ACCESS read-only
      STATUS mandatory
      DESCRIPTION
	 		    "http - max avail socket"
      ::= { fwSS-http 5 }

   fwSS-http-socket-in-use-max OBJECT-TYPE
      SYNTAX INTEGER
      ACCESS read-only
      STATUS mandatory
      DESCRIPTION
	 		    "http - socket in use max"
      ::= { fwSS-http 6 }

   fwSS-http-socket-in-use-curr OBJECT-TYPE
      SYNTAX INTEGER
      ACCESS read-only
      STATUS mandatory
      DESCRIPTION
	 		    "http - socket in use current"
      ::= { fwSS-http 7 }

   fwSS-http-socket-in-use-count OBJECT-TYPE
      SYNTAX INTEGER
      ACCESS read-only
      STATUS mandatory
      DESCRIPTION
	 		    "http - socket in use count"
      ::= { fwSS-http 8 }

   fwSS-http-sess-max OBJECT-TYPE
      SYNTAX INTEGER
      ACCESS read-only
      STATUS mandatory
      DESCRIPTION
	 		    "http - session max"
      ::= { fwSS-http 9 }

   fwSS-http-sess-curr OBJECT-TYPE
      SYNTAX INTEGER
      ACCESS read-only
      STATUS mandatory
      DESCRIPTION
	 		    "http - session current"
      ::= { fwSS-http 10 }

   fwSS-http-sess-count OBJECT-TYPE
      SYNTAX INTEGER
      ACCESS read-only
      STATUS mandatory
      DESCRIPTION
	 		    "http - session count"
      ::= { fwSS-http 11 }

   fwSS-http-auth-sess-max OBJECT-TYPE
      SYNTAX INTEGER
      ACCESS read-only
      STATUS mandatory
      DESCRIPTION
	 		    "http - auth session max"
      ::= { fwSS-http 12 }

   fwSS-http-auth-sess-curr OBJECT-TYPE
      SYNTAX INTEGER
      ACCESS read-only
      STATUS mandatory
      DESCRIPTION
	 		    "http - auth session current"
      ::= { fwSS-http 13 }

   fwSS-http-auth-sess-count OBJECT-TYPE
      SYNTAX INTEGER
      ACCESS read-only
      STATUS mandatory
      DESCRIPTION
	 		    "http - auth session count"
      ::= { fwSS-http 14 }

   fwSS-http-accepted-sess OBJECT-TYPE
      SYNTAX INTEGER
      ACCESS read-only
      STATUS mandatory
      DESCRIPTION
	 		    "http - accepted session"
      ::= { fwSS-http 15 }

   fwSS-http-rejected-sess OBJECT-TYPE
      SYNTAX INTEGER
      ACCESS read-only
      STATUS mandatory
      DESCRIPTION
	 		    "http - rejected session"
      ::= { fwSS-http 16 }

   fwSS-http-auth-failures OBJECT-TYPE
      SYNTAX INTEGER
      ACCESS read-only
      STATUS mandatory
      DESCRIPTION
	 		    "http - auth failures"
      ::= { fwSS-http 17 }

   fwSS-http-ops-cvp-sess-max OBJECT-TYPE
      SYNTAX INTEGER
      ACCESS read-only
      STATUS mandatory
      DESCRIPTION
	 		    "http - opsec cvp session max"
      ::= { fwSS-http 18 }

   fwSS-http-ops-cvp-sess-curr OBJECT-TYPE
      SYNTAX INTEGER
      ACCESS read-only
      STATUS mandatory
      DESCRIPTION
	 		    "http - opsec cvp session current"
      ::= { fwSS-http 19 }

   fwSS-http-ops-cvp-sess-count OBJECT-TYPE
      SYNTAX INTEGER
      ACCESS read-only
      STATUS mandatory
      DESCRIPTION
	 		    "http - opsec cvp session count"
      ::= { fwSS-http 20 }

   fwSS-http-ops-cvp-rej-sess OBJECT-TYPE
      SYNTAX INTEGER
      ACCESS read-only
      STATUS mandatory
      DESCRIPTION
	 		    "http - opsec cvp rej session"
      ::= { fwSS-http 21 }

   fwSS-http-ssl-encryp-sess-max OBJECT-TYPE
      SYNTAX INTEGER
      ACCESS read-only
      STATUS mandatory
      DESCRIPTION
	 		    "http - ssl encryp session max"
      ::= { fwSS-http 22 }

   fwSS-http-ssl-encryp-sess-curr OBJECT-TYPE
      SYNTAX INTEGER
      ACCESS read-only
      STATUS mandatory
      DESCRIPTION
	 		    "http - ssl encryp session current"
      ::= { fwSS-http 23 }

   fwSS-http-ssl-encryp-sess-count OBJECT-TYPE
      SYNTAX INTEGER
      ACCESS read-only
      STATUS mandatory
      DESCRIPTION
	 		    "http - ssl encryp session count"
      ::= { fwSS-http 24 }

   fwSS-http-transp-sess-max OBJECT-TYPE
      SYNTAX INTEGER
      ACCESS read-only
      STATUS mandatory
      DESCRIPTION
	 		    "http - transparent session max"
      ::= { fwSS-http 25 }

   fwSS-http-transp-sess-curr OBJECT-TYPE
      SYNTAX INTEGER
      ACCESS read-only
      STATUS mandatory
      DESCRIPTION
	 		    "http - transparent session current"
      ::= { fwSS-http 26 }

   fwSS-http-transp-sess-count OBJECT-TYPE
      SYNTAX INTEGER
      ACCESS read-only
      STATUS mandatory
      DESCRIPTION
	 		    "http - transparent session count"
      ::= { fwSS-http 27 }

   fwSS-http-proxied-sess-max OBJECT-TYPE
      SYNTAX INTEGER
      ACCESS read-only
      STATUS mandatory
      DESCRIPTION
	 		    "http - proxied session max"
      ::= { fwSS-http 28 }

   fwSS-http-proxied-sess-curr OBJECT-TYPE
      SYNTAX INTEGER
      ACCESS read-only
      STATUS mandatory
      DESCRIPTION
	 		    "http - proxied session current"
      ::= { fwSS-http 29 }

   fwSS-http-proxied-sess-count OBJECT-TYPE
      SYNTAX INTEGER
      ACCESS read-only
      STATUS mandatory
      DESCRIPTION
	 		    "http - proxied session count"
      ::= { fwSS-http 30 }

   fwSS-http-tunneled-sess-max OBJECT-TYPE
      SYNTAX INTEGER
      ACCESS read-only
      STATUS mandatory
      DESCRIPTION
	 		    "http - tunneled session max"
      ::= { fwSS-http 31 }

   fwSS-http-tunneled-sess-curr OBJECT-TYPE
      SYNTAX INTEGER
      ACCESS read-only
      STATUS mandatory
      DESCRIPTION
	 		    "http - tunneled session current"
      ::= { fwSS-http 32 }

   fwSS-http-tunneled-sess-count OBJECT-TYPE
      SYNTAX INTEGER
      ACCESS read-only
      STATUS mandatory
      DESCRIPTION
	 		    "http - tunneled session count"
      ::= { fwSS-http 33 }

   fwSS-http-ftp-sess-max OBJECT-TYPE
      SYNTAX INTEGER
      ACCESS read-only
      STATUS mandatory
      DESCRIPTION
	 		    "http - ftp session max"
      ::= { fwSS-http 34 }

   fwSS-http-ftp-sess-curr OBJECT-TYPE
      SYNTAX INTEGER
      ACCESS read-only
      STATUS mandatory
      DESCRIPTION
	 		    "http - ftp session current"
      ::= { fwSS-http 35 }

   fwSS-http-ftp-sess-count OBJECT-TYPE
      SYNTAX INTEGER
      ACCESS read-only
      STATUS mandatory
      DESCRIPTION
	 		    "http - ftp session count"
      ::= { fwSS-http 36 }

   fwSS-http-time-stamp OBJECT-TYPE
      SYNTAX DisplayString (SIZE (0..255))
      ACCESS read-only
      STATUS mandatory
      DESCRIPTION
	 		    "http - time stamp"
      ::= { fwSS-http 37 }

   fwSS-http-is-alive OBJECT-TYPE
      SYNTAX INTEGER
      ACCESS read-only
      STATUS mandatory
      DESCRIPTION
	 		    "http - is alive"
      ::= { fwSS-http 38 }

   fwSS-ftp-pid OBJECT-TYPE
      SYNTAX INTEGER
      ACCESS read-only
      STATUS mandatory
      DESCRIPTION
	 		    "ftp - pid"
      ::= { fwSS-ftp 1 }

   fwSS-ftp-proto OBJECT-TYPE
      SYNTAX INTEGER
      ACCESS read-only
      STATUS mandatory
      DESCRIPTION
	 		    "ftp - proto"
      ::= { fwSS-ftp 2 }

   fwSS-ftp-port OBJECT-TYPE
      SYNTAX INTEGER
      ACCESS read-only
      STATUS mandatory
      DESCRIPTION
	 		    "ftp - port"
      ::= { fwSS-ftp 3 }

   fwSS-ftp-logical-port OBJECT-TYPE
      SYNTAX INTEGER
      ACCESS read-only
      STATUS mandatory
      DESCRIPTION
	 		    "ftp - logical port"
      ::= { fwSS-ftp 4 }

   fwSS-ftp-max-avail-socket OBJECT-TYPE
      SYNTAX INTEGER
      ACCESS read-only
      STATUS mandatory
      DESCRIPTION
	 		    "ftp - max avail socket"
      ::= { fwSS-ftp 5 }

   fwSS-ftp-socket-in-use-max OBJECT-TYPE
      SYNTAX INTEGER
      ACCESS read-only
      STATUS mandatory
      DESCRIPTION
	 		    "ftp - socket in use max"
      ::= { fwSS-ftp 6 }

   fwSS-ftp-socket-in-use-curr OBJECT-TYPE
      SYNTAX INTEGER
      ACCESS read-only
      STATUS mandatory
      DESCRIPTION
	 		    "ftp - socket in use current"
      ::= { fwSS-ftp 7 }

   fwSS-ftp-socket-in-use-count OBJECT-TYPE
      SYNTAX INTEGER
      ACCESS read-only
      STATUS mandatory
      DESCRIPTION
	 		    "ftp - socket in use count"
      ::= { fwSS-ftp 8 }

   fwSS-ftp-sess-max OBJECT-TYPE
      SYNTAX INTEGER
      ACCESS read-only
      STATUS mandatory
      DESCRIPTION
	 		    "ftp - session max"
      ::= { fwSS-ftp 9 }

   fwSS-ftp-sess-curr OBJECT-TYPE
      SYNTAX INTEGER
      ACCESS read-only
      STATUS mandatory
      DESCRIPTION
	 		    "ftp - session current"
      ::= { fwSS-ftp 10 }

   fwSS-ftp-sess-count OBJECT-TYPE
      SYNTAX INTEGER
      ACCESS read-only
      STATUS mandatory
      DESCRIPTION
	 		    "ftp - session count"
      ::= { fwSS-ftp 11 }

   fwSS-ftp-auth-sess-max OBJECT-TYPE
      SYNTAX INTEGER
      ACCESS read-only
      STATUS mandatory
      DESCRIPTION
	 		    "ftp - auth session max"
      ::= { fwSS-ftp 12 }

   fwSS-ftp-auth-sess-curr OBJECT-TYPE
      SYNTAX INTEGER
      ACCESS read-only
      STATUS mandatory
      DESCRIPTION
	 		    "ftp - auth session current"
      ::= { fwSS-ftp 13 }

   fwSS-ftp-auth-sess-count OBJECT-TYPE
      SYNTAX INTEGER
      ACCESS read-only
      STATUS mandatory
      DESCRIPTION
	 		    "ftp - auth session count"
      ::= { fwSS-ftp 14 }

   fwSS-ftp-accepted-sess OBJECT-TYPE
      SYNTAX INTEGER
      ACCESS read-only
      STATUS mandatory
      DESCRIPTION
	 		    "ftp - accepted session"
      ::= { fwSS-ftp 15 }

   fwSS-ftp-rejected-sess OBJECT-TYPE
      SYNTAX INTEGER
      ACCESS read-only
      STATUS mandatory
      DESCRIPTION
	 		    "ftp - rejected session"
      ::= { fwSS-ftp 16 }

   fwSS-ftp-auth-failures OBJECT-TYPE
      SYNTAX INTEGER
      ACCESS read-only
      STATUS mandatory
      DESCRIPTION
	 		    "ftp - auth failures"
      ::= { fwSS-ftp 17 }

   fwSS-ftp-ops-cvp-sess-max OBJECT-TYPE
      SYNTAX INTEGER
      ACCESS read-only
      STATUS mandatory
      DESCRIPTION
	 		    "ftp - opsec cvp session max"
      ::= { fwSS-ftp 18 }

   fwSS-ftp-ops-cvp-sess-curr OBJECT-TYPE
      SYNTAX INTEGER
      ACCESS read-only
      STATUS mandatory
      DESCRIPTION
	 		    "ftp - opsec cvp session current"
      ::= { fwSS-ftp 19 }

   fwSS-ftp-ops-cvp-sess-count OBJECT-TYPE
      SYNTAX INTEGER
      ACCESS read-only
      STATUS mandatory
      DESCRIPTION
	 		    "ftp - opsec cvp session count"
      ::= { fwSS-ftp 20 }

   fwSS-ftp-ops-cvp-rej-sess OBJECT-TYPE
      SYNTAX INTEGER
      ACCESS read-only
      STATUS mandatory
      DESCRIPTION
	 		    "ftp - opsec cvp rej session"
      ::= { fwSS-ftp 21 }

   fwSS-ftp-time-stamp OBJECT-TYPE
      SYNTAX DisplayString (SIZE (0..255))
      ACCESS read-only
      STATUS mandatory
      DESCRIPTION
	 		    "ftp - time stamp"
      ::= { fwSS-ftp 22 }

   fwSS-ftp-is-alive OBJECT-TYPE
      SYNTAX INTEGER
      ACCESS read-only
      STATUS mandatory
      DESCRIPTION
	 		    "ftp - is alive"
      ::= { fwSS-ftp 23 }

   fwSS-telnet-pid OBJECT-TYPE
      SYNTAX INTEGER
      ACCESS read-only
      STATUS mandatory
      DESCRIPTION
	 		    "telnet - pid"
      ::= { fwSS-telnet 1 }

   fwSS-telnet-proto OBJECT-TYPE
      SYNTAX INTEGER
      ACCESS read-only
      STATUS mandatory
      DESCRIPTION
	 		    "telnet - proto"
      ::= { fwSS-telnet 2 }

   fwSS-telnet-port OBJECT-TYPE
      SYNTAX INTEGER
      ACCESS read-only
      STATUS mandatory
      DESCRIPTION
	 		    "telnet - port"
      ::= { fwSS-telnet 3 }

   fwSS-telnet-logical-port OBJECT-TYPE
      SYNTAX INTEGER
      ACCESS read-only
      STATUS mandatory
      DESCRIPTION
	 		    "telnet - logical port"
      ::= { fwSS-telnet 4 }

   fwSS-telnet-max-avail-socket OBJECT-TYPE
      SYNTAX INTEGER
      ACCESS read-only
      STATUS mandatory
      DESCRIPTION
	 		    "telnet - max avail socket"
      ::= { fwSS-telnet 5 }

   fwSS-telnet-socket-in-use-max OBJECT-TYPE
      SYNTAX INTEGER
      ACCESS read-only
      STATUS mandatory
      DESCRIPTION
	 		    "telnet - socket in use max"
      ::= { fwSS-telnet 6 }

   fwSS-telnet-socket-in-use-curr OBJECT-TYPE
      SYNTAX INTEGER
      ACCESS read-only
      STATUS mandatory
      DESCRIPTION
	 		    "telnet - socket in use current"
      ::= { fwSS-telnet 7 }

   fwSS-telnet-socket-in-use-count OBJECT-TYPE
      SYNTAX INTEGER
      ACCESS read-only
      STATUS mandatory
      DESCRIPTION
	 		    "telnet - socket in use count"
      ::= { fwSS-telnet 8 }

   fwSS-telnet-sess-max OBJECT-TYPE
      SYNTAX INTEGER
      ACCESS read-only
      STATUS mandatory
      DESCRIPTION
	 		    "telnet - session max"
      ::= { fwSS-telnet 9 }

   fwSS-telnet-sess-curr OBJECT-TYPE
      SYNTAX INTEGER
      ACCESS read-only
      STATUS mandatory
      DESCRIPTION
	 		    "telnet - session current"
      ::= { fwSS-telnet 10 }

   fwSS-telnet-sess-count OBJECT-TYPE
      SYNTAX INTEGER
      ACCESS read-only
      STATUS mandatory
      DESCRIPTION
	 		    "telnet - session count"
      ::= { fwSS-telnet 11 }

   fwSS-telnet-auth-sess-max OBJECT-TYPE
      SYNTAX INTEGER
      ACCESS read-only
      STATUS mandatory
      DESCRIPTION
	 		    "telnet - auth session max"
      ::= { fwSS-telnet 12 }

   fwSS-telnet-auth-sess-curr OBJECT-TYPE
      SYNTAX INTEGER
      ACCESS read-only
      STATUS mandatory
      DESCRIPTION
	 		    "telnet - auth session current"
      ::= { fwSS-telnet 13 }

   fwSS-telnet-auth-sess-count OBJECT-TYPE
      SYNTAX INTEGER
      ACCESS read-only
      STATUS mandatory
      DESCRIPTION
	 		    "telnet - auth session count"
      ::= { fwSS-telnet 14 }

   fwSS-telnet-accepted-sess OBJECT-TYPE
      SYNTAX INTEGER
      ACCESS read-only
      STATUS mandatory
      DESCRIPTION
	 		    "telnet - accepted session"
      ::= { fwSS-telnet 15 }

   fwSS-telnet-rejected-sess OBJECT-TYPE
      SYNTAX INTEGER
      ACCESS read-only
      STATUS mandatory
      DESCRIPTION
	 		    "telnet - rejected session"
      ::= { fwSS-telnet 16 }

   fwSS-telnet-auth-failures OBJECT-TYPE
      SYNTAX INTEGER
      ACCESS read-only
      STATUS mandatory
      DESCRIPTION
	 		    "telnet - auth failures"
      ::= { fwSS-telnet 17 }

   fwSS-telnet-time-stamp OBJECT-TYPE
      SYNTAX DisplayString (SIZE (0..255))
      ACCESS read-only
      STATUS mandatory
      DESCRIPTION
	 		    "telnet - time stamp"
      ::= { fwSS-telnet 18 }

   fwSS-telnet-is-alive OBJECT-TYPE
      SYNTAX INTEGER
      ACCESS read-only
      STATUS mandatory
      DESCRIPTION
	 		    "telnet - is alive"
      ::= { fwSS-telnet 19 }

   fwSS-rlogin-pid OBJECT-TYPE
      SYNTAX INTEGER
      ACCESS read-only
      STATUS mandatory
      DESCRIPTION
	 		    "rlogin - pid"
      ::= { fwSS-rlogin 1 }

   fwSS-rlogin-proto OBJECT-TYPE
      SYNTAX INTEGER
      ACCESS read-only
      STATUS mandatory
      DESCRIPTION
	 		    "rlogin - proto"
      ::= { fwSS-rlogin 2 }

   fwSS-rlogin-port OBJECT-TYPE
      SYNTAX INTEGER
      ACCESS read-only
      STATUS mandatory
      DESCRIPTION
	 		    "rlogin - port"
      ::= { fwSS-rlogin 3 }

   fwSS-rlogin-logical-port OBJECT-TYPE
      SYNTAX INTEGER
      ACCESS read-only
      STATUS mandatory
      DESCRIPTION
	 		    "rlogin - logical port"
      ::= { fwSS-rlogin 4 }

   fwSS-rlogin-max-avail-socket OBJECT-TYPE
      SYNTAX INTEGER
      ACCESS read-only
      STATUS mandatory
      DESCRIPTION
	 		    "rlogin - max avail socket"
      ::= { fwSS-rlogin 5 }

   fwSS-rlogin-socket-in-use-max OBJECT-TYPE
      SYNTAX INTEGER
      ACCESS read-only
      STATUS mandatory
      DESCRIPTION
	 		    "rlogin - socket in use max"
      ::= { fwSS-rlogin 6 }

   fwSS-rlogin-socket-in-use-curr OBJECT-TYPE
      SYNTAX INTEGER
      ACCESS read-only
      STATUS mandatory
      DESCRIPTION
	 		    "rlogin - socket in use current"
      ::= { fwSS-rlogin 7 }

   fwSS-rlogin-socket-in-use-count OBJECT-TYPE
      SYNTAX INTEGER
      ACCESS read-only
      STATUS mandatory
      DESCRIPTION
	 		    "rlogin - socket in use count"
      ::= { fwSS-rlogin 8 }

   fwSS-rlogin-sess-max OBJECT-TYPE
      SYNTAX INTEGER
      ACCESS read-only
      STATUS mandatory
      DESCRIPTION
	 		    "rlogin - session max"
      ::= { fwSS-rlogin 9 }

   fwSS-rlogin-sess-curr OBJECT-TYPE
      SYNTAX INTEGER
      ACCESS read-only
      STATUS mandatory
      DESCRIPTION
	 		    "rlogin - session current"
      ::= { fwSS-rlogin 10 }

   fwSS-rlogin-sess-count OBJECT-TYPE
      SYNTAX INTEGER
      ACCESS read-only
      STATUS mandatory
      DESCRIPTION
	 		    "rlogin - session count"
      ::= { fwSS-rlogin 11 }

   fwSS-rlogin-auth-sess-max OBJECT-TYPE
      SYNTAX INTEGER
      ACCESS read-only
      STATUS mandatory
      DESCRIPTION
	 		    "rlogin - auth session max"
      ::= { fwSS-rlogin 12 }

   fwSS-rlogin-auth-sess-curr OBJECT-TYPE
      SYNTAX INTEGER
      ACCESS read-only
      STATUS mandatory
      DESCRIPTION
	 		    "rlogin - auth session current"
      ::= { fwSS-rlogin 13 }

   fwSS-rlogin-auth-sess-count OBJECT-TYPE
      SYNTAX INTEGER
      ACCESS read-only
      STATUS mandatory
      DESCRIPTION
	 		    "rlogin - auth session count"
      ::= { fwSS-rlogin 14 }

   fwSS-rlogin-accepted-sess OBJECT-TYPE
      SYNTAX INTEGER
      ACCESS read-only
      STATUS mandatory
      DESCRIPTION
	 		    "rlogin - accepted session"
      ::= { fwSS-rlogin 15 }

   fwSS-rlogin-rejected-sess OBJECT-TYPE
      SYNTAX INTEGER
      ACCESS read-only
      STATUS mandatory
      DESCRIPTION
	 		    "rlogin - rejected session"
      ::= { fwSS-rlogin 16 }

   fwSS-rlogin-auth-failures OBJECT-TYPE
      SYNTAX INTEGER
      ACCESS read-only
      STATUS mandatory
      DESCRIPTION
	 		    "rlogin - auth failures"
      ::= { fwSS-rlogin 17 }

   fwSS-rlogin-time-stamp OBJECT-TYPE
      SYNTAX DisplayString (SIZE (0..255))
      ACCESS read-only
      STATUS mandatory
      DESCRIPTION
	 		    "rlogin - time stamp"
      ::= { fwSS-rlogin 18 }

   fwSS-rlogin-is-alive OBJECT-TYPE
      SYNTAX INTEGER
      ACCESS read-only
      STATUS mandatory
      DESCRIPTION
	 		    "rlogin - is alive"
      ::= { fwSS-rlogin 19 }

   fwSS-ufp-ops-ufp-sess-max OBJECT-TYPE
      SYNTAX INTEGER
      ACCESS read-only
      STATUS mandatory
      DESCRIPTION
	 		    "ufp - session max"
      ::= { fwSS-ufp 1 }

   fwSS-ufp-ops-ufp-sess-curr OBJECT-TYPE
      SYNTAX INTEGER
      ACCESS read-only
      STATUS mandatory
      DESCRIPTION
	 		    "ufp - session current"
      ::= { fwSS-ufp 2 }

   fwSS-ufp-ops-ufp-sess-count OBJECT-TYPE
      SYNTAX INTEGER
      ACCESS read-only
      STATUS mandatory
      DESCRIPTION
	 		    "ufp - session count"
      ::= { fwSS-ufp 3 }

   fwSS-ufp-ops-ufp-rej-sess OBJECT-TYPE
      SYNTAX INTEGER
      ACCESS read-only
      STATUS mandatory
      DESCRIPTION
	 		    "ufp - rej session"
      ::= { fwSS-ufp 4 }

   fwSS-ufp-time-stamp OBJECT-TYPE
      SYNTAX DisplayString (SIZE (0..255))
      ACCESS read-only
      STATUS mandatory
      DESCRIPTION
	 		    "ufp - time stamp"
      ::= { fwSS-ufp 5 }

   fwSS-ufp-is-alive OBJECT-TYPE
      SYNTAX INTEGER
      ACCESS read-only
      STATUS mandatory
      DESCRIPTION
	 		    "ufp - is alive"
      ::= { fwSS-ufp 6 }

   fwSS-smtp-pid OBJECT-TYPE
      SYNTAX INTEGER
      ACCESS read-only
      STATUS mandatory
      DESCRIPTION
	 		    "smtp - pid"
      ::= { fwSS-smtp 1 }

   fwSS-smtp-proto OBJECT-TYPE
      SYNTAX INTEGER
      ACCESS read-only
      STATUS mandatory
      DESCRIPTION
	 		    "smtp - proto"
      ::= { fwSS-smtp 2 }

   fwSS-smtp-port OBJECT-TYPE
      SYNTAX INTEGER
      ACCESS read-only
      STATUS mandatory
      DESCRIPTION
	 		    "smtp - port"
      ::= { fwSS-smtp 3 }

   fwSS-smtp-logical-port OBJECT-TYPE
      SYNTAX INTEGER
      ACCESS read-only
      STATUS mandatory
      DESCRIPTION
	 		    "smtp - logical port"
      ::= { fwSS-smtp 4 }

   fwSS-smtp-max-avail-socket OBJECT-TYPE
      SYNTAX INTEGER
      ACCESS read-only
      STATUS mandatory
      DESCRIPTION
	 		    "smtp - max avail socket"
      ::= { fwSS-smtp 5 }

   fwSS-smtp-socket-in-use-max OBJECT-TYPE
      SYNTAX INTEGER
      ACCESS read-only
      STATUS mandatory
      DESCRIPTION
	 		    "smtp - socket in use max"
      ::= { fwSS-smtp 6 }

   fwSS-smtp-socket-in-use-curr OBJECT-TYPE
      SYNTAX INTEGER
      ACCESS read-only
      STATUS mandatory
      DESCRIPTION
	 		    "smtp - socket in use current"
      ::= { fwSS-smtp 7 }

   fwSS-smtp-socket-in-use-count OBJECT-TYPE
      SYNTAX INTEGER
      ACCESS read-only
      STATUS mandatory
      DESCRIPTION
	 		    "smtp - socket in use count"
      ::= { fwSS-smtp 8 }

   fwSS-smtp-sess-max OBJECT-TYPE
      SYNTAX INTEGER
      ACCESS read-only
      STATUS mandatory
      DESCRIPTION
	 		    "smtp - session max"
      ::= { fwSS-smtp 9 }

   fwSS-smtp-sess-curr OBJECT-TYPE
      SYNTAX INTEGER
      ACCESS read-only
      STATUS mandatory
      DESCRIPTION
	 		    "smtp - session current"
      ::= { fwSS-smtp 10 }

   fwSS-smtp-sess-count OBJECT-TYPE
      SYNTAX INTEGER
      ACCESS read-only
      STATUS mandatory
      DESCRIPTION
	 		    "smtp - session count"
      ::= { fwSS-smtp 11 }

   fwSS-smtp-auth-sess-max OBJECT-TYPE
      SYNTAX INTEGER
      ACCESS read-only
      STATUS mandatory
      DESCRIPTION
	 		    "smtp - auth session max"
      ::= { fwSS-smtp 12 }

   fwSS-smtp-auth-sess-curr OBJECT-TYPE
      SYNTAX INTEGER
      ACCESS read-only
      STATUS mandatory
      DESCRIPTION
	 		    "smtp - auth session current"
      ::= { fwSS-smtp 13 }

   fwSS-smtp-auth-sess-count OBJECT-TYPE
      SYNTAX INTEGER
      ACCESS read-only
      STATUS mandatory
      DESCRIPTION
	 		    "smtp - auth session count"
      ::= { fwSS-smtp 14 }

   fwSS-smtp-accepted-sess OBJECT-TYPE
      SYNTAX INTEGER
      ACCESS read-only
      STATUS mandatory
      DESCRIPTION
	 		    "smtp - accepted session"
      ::= { fwSS-smtp 15 }

   fwSS-smtp-rejected-sess OBJECT-TYPE
      SYNTAX INTEGER
      ACCESS read-only
      STATUS mandatory
      DESCRIPTION
	 		    "smtp - rejected session"
      ::= { fwSS-smtp 16 }

   fwSS-smtp-auth-failures OBJECT-TYPE
      SYNTAX INTEGER
      ACCESS read-only
      STATUS mandatory
      DESCRIPTION
	 		    "smtp - auth failures"
      ::= { fwSS-smtp 17 }

   fwSS-smtp-mail-max OBJECT-TYPE
      SYNTAX INTEGER
      ACCESS read-only
      STATUS mandatory
      DESCRIPTION
	 		    "smtp - mail max"
      ::= { fwSS-smtp 18 }

   fwSS-smtp-mail-curr OBJECT-TYPE
      SYNTAX INTEGER
      ACCESS read-only
      STATUS mandatory
      DESCRIPTION
	 		    "smtp - mail curr"
      ::= { fwSS-smtp 19 }

   fwSS-smtp-mail-count OBJECT-TYPE
      SYNTAX INTEGER
      ACCESS read-only
      STATUS mandatory
      DESCRIPTION
	 		    "smtp - mail count"
      ::= { fwSS-smtp 20 }

   fwSS-smtp-outgoing-mail-max OBJECT-TYPE
      SYNTAX INTEGER
      ACCESS read-only
      STATUS mandatory
      DESCRIPTION
	 		    "smtp - outgoing mail max"
      ::= { fwSS-smtp 21 }

   fwSS-smtp-outgoing-mail-curr OBJECT-TYPE
      SYNTAX INTEGER
      ACCESS read-only
      STATUS mandatory
      DESCRIPTION
	 		    "smtp - outgoing mail curr"
      ::= { fwSS-smtp 22 }

   fwSS-smtp-outgoing-mail-count OBJECT-TYPE
      SYNTAX INTEGER
      ACCESS read-only
      STATUS mandatory
      DESCRIPTION
	 		    "smtp - outgoing mail count"
      ::= { fwSS-smtp 23 }

   fwSS-smtp-max-mail-on-conn OBJECT-TYPE
      SYNTAX INTEGER
      ACCESS read-only
      STATUS mandatory
      DESCRIPTION
	 		    "smtp - max mail on conn"
      ::= { fwSS-smtp 24 }

   fwSS-smtp-total-mails OBJECT-TYPE
      SYNTAX INTEGER
      ACCESS read-only
      STATUS mandatory
      DESCRIPTION
	 		    "smtp - total mails"
      ::= { fwSS-smtp 25 }

   fwSS-smtp-time-stamp OBJECT-TYPE
      SYNTAX DisplayString (SIZE (0..255))
      ACCESS read-only
      STATUS mandatory
      DESCRIPTION
	 		    "smtp - time stamp"
      ::= { fwSS-smtp 26 }

   fwSS-smtp-is-alive OBJECT-TYPE
      SYNTAX INTEGER
      ACCESS read-only
      STATUS mandatory
      DESCRIPTION
	 		    "smtp - is alive"
      ::= { fwSS-smtp 27 }


   -- the VPN status
	 -- Overall statistics and state

   cpvGeneral		  	OBJECT IDENTIFIER ::= { vpn 4 }
   cpvIpsec        OBJECT IDENTIFIER ::= { vpn 5 }
   cpvFwz         OBJECT IDENTIFIER ::= { vpn 6 }
   cpvAccelerator     OBJECT IDENTIFIER ::= { vpn 8 }
   cpvIKE         OBJECT IDENTIFIER ::= { vpn 9 }
   cpvIPsec        OBJECT IDENTIFIER ::= { vpn 10 }
   cpvStatistics     OBJECT IDENTIFIER ::= { cpvGeneral 1 }
   cpvErrors       OBJECT IDENTIFIER ::= { cpvGeneral 2 }
   cpvSaStatistics    OBJECT IDENTIFIER ::= { cpvIpsec 2 }
   cpvSaErrors      OBJECT IDENTIFIER ::= { cpvIpsec 3 }
   cpvIpsecStatistics   OBJECT IDENTIFIER ::= { cpvIpsec 4 }
   cpvFwzStatistics    OBJECT IDENTIFIER ::= { cpvFwz 1 }
   cpvFwzErrors      OBJECT IDENTIFIER ::= { cpvFwz 2 }
   cpvHwAccelGeneral   OBJECT IDENTIFIER ::= { cpvAccelerator 1 }
   cpvHwAccelStatistics  OBJECT IDENTIFIER ::= { cpvAccelerator 2 }
   cpvIKEglobals     OBJECT IDENTIFIER ::= { cpvIKE 1 }
   cpvIKEerrors      OBJECT IDENTIFIER ::= { cpvIKE 2 }
   cpvIPsecNIC      OBJECT IDENTIFIER ::= { cpvIPsec 1 }

   cpvProdName OBJECT-TYPE
	    SYNTAX DisplayString (SIZE (0..255))
	    ACCESS read-only
	    STATUS mandatory
	    DESCRIPTION
	    	  "Product name"
	    ::= { vpn 1 }

   cpvVerMajor OBJECT-TYPE
	    SYNTAX INTEGER
	    ACCESS read-only
	    STATUS mandatory
	    DESCRIPTION
	    	  "Major version"
	    ::= { vpn 2 }

	 cpvVerMinor OBJECT-TYPE
	    SYNTAX INTEGER
	    ACCESS read-only
	    STATUS mandatory
	    DESCRIPTION
	    	  "Minor version"
	    ::= { vpn 3 }

   cpvEncPackets OBJECT-TYPE
	    SYNTAX DisplayString
	    ACCESS read-only
	    STATUS mandatory
	    DESCRIPTION
	    	  "Encrypted packets"
	    ::= { cpvStatistics 1 }

   cpvDecPackets OBJECT-TYPE
	    SYNTAX DisplayString
	    ACCESS read-only
	    STATUS mandatory
	    DESCRIPTION
	    	  "Decrypted packets"
	    ::= { cpvStatistics 2 }

   cpvErrOut OBJECT-TYPE
	    SYNTAX DisplayString
	    ACCESS read-only
	    STATUS mandatory
	    DESCRIPTION
	    	  "Encryption errors"
	    ::= { cpvErrors 1 }

   cpvErrIn OBJECT-TYPE
	    SYNTAX DisplayString
	    ACCESS read-only
	    STATUS mandatory
	    DESCRIPTION
	    	  "Decryption errors"
	    ::= { cpvErrors 2 }

	 cpvErrIke OBJECT-TYPE
	    SYNTAX DisplayString
	    ACCESS read-only
	    STATUS optional
	    DESCRIPTION
	    	  "IKE errors"
	    ::= { cpvErrors 3 }

   cpvErrPolicy OBJECT-TYPE
	    SYNTAX DisplayString
	    ACCESS read-only
	    STATUS mandatory
	    DESCRIPTION
	    	  "Policy errors"
	    ::= { cpvErrors 4 }


	 cpvCurrEspSAsIn OBJECT-TYPE
	    SYNTAX DisplayString
	    ACCESS read-only
	    STATUS mandatory
	    DESCRIPTION
	    	  "IPsec current Inbound ESP SAs"
	    ::= { cpvSaStatistics 1 }

	 cpvTotalEspSAsIn OBJECT-TYPE
	    SYNTAX DisplayString
	    ACCESS read-only
	    STATUS mandatory
	    DESCRIPTION
	    	  "IPsec total Inbound ESP SAs"
	    ::= { cpvSaStatistics 2 }

	 cpvCurrEspSAsOut OBJECT-TYPE
	    SYNTAX DisplayString
	    ACCESS read-only
	    STATUS mandatory
	    DESCRIPTION
	    	  "IPsec current Outbound ESP SAs"
	    ::= { cpvSaStatistics 3 }

	 cpvTotalEspSAsOut OBJECT-TYPE
	    SYNTAX DisplayString
	    ACCESS read-only
	    STATUS mandatory
	    DESCRIPTION
	    	  "IPsec total Outbound ESP SAs"
	    ::= { cpvSaStatistics 4 }

	 cpvCurrAhSAsIn OBJECT-TYPE
	    SYNTAX DisplayString
	    ACCESS read-only
	    STATUS mandatory
	    DESCRIPTION
	    	  "IPsec current Inbound AH SAs"
	    ::= { cpvSaStatistics 5 }

	 cpvTotalAhSAsIn OBJECT-TYPE
	    SYNTAX DisplayString
	    ACCESS read-only
	    STATUS mandatory
	    DESCRIPTION
	    	  "IPsec total Inbound AH SAs"
	    ::= { cpvSaStatistics 6 }

	 cpvCurrAhSAsOut OBJECT-TYPE
	    SYNTAX DisplayString
	    ACCESS read-only
	    STATUS mandatory
	    DESCRIPTION
	    	  "IPsec current Outbound AH SAs"
	    ::= { cpvSaStatistics 7 }

	 cpvTotalAhSAsOut OBJECT-TYPE
	    SYNTAX DisplayString
	    ACCESS read-only
	    STATUS mandatory
	    DESCRIPTION
	    	  "IPsec total Outbound AH SAs"
	    ::= { cpvSaStatistics 8 }

	 cpvMaxConncurEspSAsIn OBJECT-TYPE
	    SYNTAX DisplayString
	    ACCESS read-only
	    STATUS mandatory
	    DESCRIPTION
	    	  "IPsec max concurrent Inbound ESP SAs"
	    ::= { cpvSaStatistics 9 }

	 cpvMaxConncurEspSAsOut OBJECT-TYPE
	    SYNTAX DisplayString
	    ACCESS read-only
	    STATUS mandatory
	    DESCRIPTION
	    	  "IPsec max concurrent Outbound ESP SAs"
	    ::= { cpvSaStatistics 10 }

	 cpvMaxConncurAhSAsIn OBJECT-TYPE
	    SYNTAX DisplayString
	    ACCESS read-only
	    STATUS mandatory
	    DESCRIPTION
	    	  "IPsec max concurrent Inbound AH SAs"
	    ::= { cpvSaStatistics 11 }

	 cpvMaxConncurAhSAsOut OBJECT-TYPE
	    SYNTAX DisplayString
	    ACCESS read-only
	    STATUS mandatory
	    DESCRIPTION
	    	  "IPsec max concurrent Outbound AH SAs"
	    ::= { cpvSaStatistics 12 }

	 cpvSaDecrErr OBJECT-TYPE
	    SYNTAX DisplayString
	    ACCESS read-only
	    STATUS mandatory
	    DESCRIPTION
	    	  "IPsec decryption errors"
	    ::= { cpvSaErrors 1 }

	 cpvSaAuthErr OBJECT-TYPE
	    SYNTAX DisplayString
	    ACCESS read-only
	    STATUS mandatory
	    DESCRIPTION
	    	  "IPsec authentication errors"
	    ::= { cpvSaErrors 2 }

	 cpvSaReplayErr OBJECT-TYPE
	    SYNTAX DisplayString
	    ACCESS read-only
	    STATUS mandatory
	    DESCRIPTION
	    	  "IPsec replay errors"
	    ::= { cpvSaErrors 3 }

	 cpvSaPolicyErr OBJECT-TYPE
	    SYNTAX DisplayString
	    ACCESS read-only
	    STATUS mandatory
	    DESCRIPTION
	    	  "IPsec policy errors"
	    ::= { cpvSaErrors 4 }

	 cpvSaOtherErrIn OBJECT-TYPE
	    SYNTAX DisplayString
	    ACCESS read-only
	    STATUS mandatory
	    DESCRIPTION
	    	  "IPsec other inbound errors"
	    ::= { cpvSaErrors 5 }

	 cpvSaOtherErrOut OBJECT-TYPE
	    SYNTAX DisplayString
	    ACCESS read-only
	    STATUS mandatory
	    DESCRIPTION
	    	  "IPsec other outbound errors"
	    ::= { cpvSaErrors 6 }

	 cpvSaUnknownSpiErr OBJECT-TYPE
	    SYNTAX DisplayString
	    ACCESS read-only
	    STATUS mandatory
	    DESCRIPTION
	    	  "IPsec unknown SPI errors"
	    ::= { cpvSaErrors 7 }


	 cpvIpsecUdpEspEncPkts OBJECT-TYPE
	    SYNTAX DisplayString
	    ACCESS read-only
	    STATUS mandatory
	    DESCRIPTION
	    	  "IPsec UDP ESP encrypted packets"
	    ::= { cpvIpsecStatistics 1 }

	 cpvIpsecUdpEspDecPkts OBJECT-TYPE
	    SYNTAX DisplayString
	    ACCESS read-only
	    STATUS mandatory
	    DESCRIPTION
	    	  "IPsec UDP ESP decrypted packets"
	    ::= { cpvIpsecStatistics 2 }

	 cpvIpsecAhEncPkts OBJECT-TYPE
	    SYNTAX DisplayString
	    ACCESS read-only
	    STATUS mandatory
	    DESCRIPTION
	    	  "IPsec AH encrypted packets"
	    ::= { cpvIpsecStatistics 3 }

	 cpvIpsecAhDecPkts OBJECT-TYPE
	    SYNTAX DisplayString
	    ACCESS read-only
	    STATUS mandatory
	    DESCRIPTION
	    	  "IPsec AH decrypted packets"
	    ::= { cpvIpsecStatistics 4 }

	 cpvIpsecEspEncPkts OBJECT-TYPE
	    SYNTAX DisplayString
	    ACCESS read-only
	    STATUS mandatory
	    DESCRIPTION
	    	  "IPsec ESP encrypted packets"
	    ::= { cpvIpsecStatistics 5 }

	 cpvIpsecEspDecPkts OBJECT-TYPE
	    SYNTAX DisplayString
	    ACCESS read-only
	    STATUS mandatory
	    DESCRIPTION
	    	  "IPsec ESP decrypted packets"
	    ::= { cpvIpsecStatistics 6 }

   cpvIpsecDecomprBytesBefore OBJECT-TYPE
	    SYNTAX DisplayString
	    ACCESS read-only
	    STATUS mandatory
	    DESCRIPTION
	    	  "IPsec bytes before decompression"
	    ::= { cpvIpsecStatistics 7 }


	 cpvIpsecDecomprBytesAfter OBJECT-TYPE
	    SYNTAX DisplayString
	    ACCESS read-only
	    STATUS mandatory
	    DESCRIPTION
	    	  "IPsec bytes after decompression"
	    ::= { cpvIpsecStatistics 8 }

	 cpvIpsecDecomprOverhead OBJECT-TYPE
	    SYNTAX DisplayString
	    ACCESS read-only
	    STATUS mandatory
	    DESCRIPTION
	    	  "IPsec bytes decompression overhead"
	    ::= { cpvIpsecStatistics 9 }

	 cpvIpsecDecomprPkts OBJECT-TYPE
	    SYNTAX DisplayString
	    ACCESS read-only
	    STATUS mandatory
	    DESCRIPTION
	    	  "IPsec packets decompressed"
	    ::= { cpvIpsecStatistics 10 }

	 cpvIpsecDecomprErr OBJECT-TYPE
	    SYNTAX DisplayString
	    ACCESS read-only
	    STATUS mandatory
	    DESCRIPTION
	    	  "IPsec decompression errors"
	    ::= { cpvIpsecStatistics 11 }

	 cpvIpsecComprBytesBefore OBJECT-TYPE
	    SYNTAX DisplayString
	    ACCESS read-only
	    STATUS mandatory
	    DESCRIPTION
	    	  "IPsec bytes before compression"
	    ::= { cpvIpsecStatistics 12 }

   cpvIpsecComprBytesAfter OBJECT-TYPE
	    SYNTAX DisplayString
	    ACCESS read-only
	    STATUS mandatory
	    DESCRIPTION
	    	  "IPsec bytes after compression"
	    ::= { cpvIpsecStatistics 13 }

 	 cpvIpsecComprOverhead OBJECT-TYPE
	    SYNTAX DisplayString
	    ACCESS read-only
	    STATUS mandatory
	    DESCRIPTION
	    	  "IPsec bytes compression overhead"
	    ::= { cpvIpsecStatistics 14 }

	 cpvIpsecNonCompressibleBytes OBJECT-TYPE
	    SYNTAX DisplayString
	    ACCESS read-only
	    STATUS mandatory
	    DESCRIPTION
	    	  "IPsec bytes non compressible"
	    ::= { cpvIpsecStatistics 15 }

   cpvIpsecCompressiblePkts OBJECT-TYPE
	    SYNTAX DisplayString
	    ACCESS read-only
	    STATUS mandatory
	    DESCRIPTION
	    	  "IPsec packets compressed"
	    ::= { cpvIpsecStatistics 16 }

   cpvIpsecNonCompressiblePkts OBJECT-TYPE
	    SYNTAX DisplayString
	    ACCESS read-only
	    STATUS mandatory
	    DESCRIPTION
	    	  "IPsec packets non compressible"
	    ::= { cpvIpsecStatistics 17 }

	 cpvIpsecComprErrors OBJECT-TYPE
	    SYNTAX DisplayString
	    ACCESS read-only
	    STATUS mandatory
	    DESCRIPTION
	    	  "IPsec compression errors"
	    ::= { cpvIpsecStatistics 18 }

	 cpvIpsecEspEncBytes OBJECT-TYPE
	    SYNTAX DisplayString
	    ACCESS read-only
	    STATUS mandatory
	    DESCRIPTION
	    	  "IPsec ESP encrypted bytes"
	    ::= { cpvIpsecStatistics 19 }

	 cpvIpsecEspDecBytes OBJECT-TYPE
	    SYNTAX DisplayString
	    ACCESS read-only
	    STATUS mandatory
	    DESCRIPTION
	    	  "IPsec ESP decrypted bytes"
	    ::= { cpvIpsecStatistics 20 }

   cpvFwzEncapsEncPkts OBJECT-TYPE
	    SYNTAX INTEGER
	    ACCESS read-only
	    STATUS mandatory
	    DESCRIPTION
	    	  "Fwz encapsulated encrypted packets"
	    ::= { cpvFwzStatistics 1 }

   cpvFwzEncapsDecPkts OBJECT-TYPE
	    SYNTAX INTEGER
	    ACCESS read-only
	    STATUS mandatory
	    DESCRIPTION
	    	  "Fwz encapsulated decrypted packets"
	    ::= { cpvFwzStatistics 2 }

   cpvFwzEncPkts OBJECT-TYPE
	    SYNTAX INTEGER
	    ACCESS read-only
	    STATUS mandatory
	    DESCRIPTION
	    	  "Fwz encrypted packets"
	    ::= { cpvFwzStatistics 3 }

	 cpvFwzDecPkts OBJECT-TYPE
	    SYNTAX INTEGER
	    ACCESS read-only
	    STATUS mandatory
	    DESCRIPTION
	    	  "Fwz decrypted packets"
	    ::= { cpvFwzStatistics 4 }


	 cpvFwzEncapsEncErrs OBJECT-TYPE
	    SYNTAX INTEGER
	    ACCESS read-only
	    STATUS mandatory
	    DESCRIPTION
	    	  "Fwz encapsulated encryption errors"
	    ::= { cpvFwzErrors 1 }

   cpvFwzEncapsDecErrs OBJECT-TYPE
	    SYNTAX INTEGER
	    ACCESS read-only
	    STATUS mandatory
	    DESCRIPTION
	    	  "Fwz encapsulated decryption errors"
	    ::= { cpvFwzErrors 2 }

   cpvFwzEncErrs OBJECT-TYPE
	    SYNTAX INTEGER
	    ACCESS read-only
	    STATUS mandatory
	    DESCRIPTION
	    	  "Fwz encryption errors"
	    ::= { cpvFwzErrors 3 }

	 cpvFwzDecErrs OBJECT-TYPE
	    SYNTAX INTEGER
	    ACCESS read-only
	    STATUS mandatory
	    DESCRIPTION
	    	  "Fwz decryption errors"
	    ::= { cpvFwzErrors 4 }

   cpvHwAccelVendor OBJECT-TYPE
	    SYNTAX DisplayString
	    ACCESS read-only
	    STATUS mandatory
	    DESCRIPTION
	    	  "HW accel. vendor"
	    ::= { cpvHwAccelGeneral 1 }

   cpvHwAccelStatus OBJECT-TYPE
	    SYNTAX DisplayString
	    ACCESS read-only
	    STATUS mandatory
	    DESCRIPTION
	    	  "HW accel. status"
	    ::= { cpvHwAccelGeneral 2 }

   cpvHwAccelDriverMajorVer OBJECT-TYPE
	    SYNTAX INTEGER
	    ACCESS read-only
	    STATUS mandatory
	    DESCRIPTION
	    	  "HW accel. driver major version"
	    ::= { cpvHwAccelGeneral 3 }

   cpvHwAccelDriverMinorVer OBJECT-TYPE
	    SYNTAX INTEGER
	    ACCESS read-only
	    STATUS mandatory
	    DESCRIPTION
	    	  "HW accel. driver minor version"
	    ::= { cpvHwAccelGeneral 4 }

   cpvHwAccelEspEncPkts OBJECT-TYPE
	    SYNTAX DisplayString
	    ACCESS read-only
	    STATUS mandatory
	    DESCRIPTION
	    	  "HW accel. encrypted IPsec ESP packets"
	    ::= { cpvHwAccelStatistics 1 }


   cpvHwAccelEspDecPkts OBJECT-TYPE
	    SYNTAX DisplayString
	    ACCESS read-only
	    STATUS mandatory
	    DESCRIPTION
	    	  "HW accel. decrypted IPsec ESP packets"
	    ::= { cpvHwAccelStatistics 2 }

	cpvHwAccelEspEncBytes OBJECT-TYPE
	    SYNTAX DisplayString
	    ACCESS read-only
	    STATUS mandatory
	    DESCRIPTION
	    	  "HW accel. encrypted IPsec ESP bytes"
	    ::= { cpvHwAccelStatistics 3 }

	cpvHwAccelEspDecBytes OBJECT-TYPE
	    SYNTAX DisplayString
	    ACCESS read-only
	    STATUS mandatory
	    DESCRIPTION
	    	  "HW accel. decrypted IPsec ESP bytes"
	    ::= { cpvHwAccelStatistics 4 }

	cpvHwAccelAhEncPkts OBJECT-TYPE
	    SYNTAX DisplayString
	    ACCESS read-only
	    STATUS mandatory
	    DESCRIPTION
	    	  "HW accel. encrypted IPsec AH packets"
	    ::= { cpvHwAccelStatistics 5 }

	cpvHwAccelAhDecPkts OBJECT-TYPE
	    SYNTAX DisplayString
	    ACCESS read-only
	    STATUS mandatory
	    DESCRIPTION
	    	  "HW accel. decrypted IPsec AH packets"
	    ::= { cpvHwAccelStatistics 6 }

	cpvHwAccelAhEncBytes OBJECT-TYPE
	    SYNTAX DisplayString
	    ACCESS read-only
	    STATUS mandatory
	    DESCRIPTION
	    	  "HW accel. encrypted IPsec AH bytes"
	    ::= { cpvHwAccelStatistics 7 }


   cpvHwAccelAhDecBytes OBJECT-TYPE
	    SYNTAX DisplayString
	    ACCESS read-only
	    STATUS mandatory
	    DESCRIPTION
	    	  "HW accel. decrypted IPsec AH bytes"
	    ::= { cpvHwAccelStatistics 8 }


   cpvIKECurrSAs OBJECT-TYPE
	    SYNTAX DisplayString
	    ACCESS read-only
	    STATUS mandatory
	    DESCRIPTION
	    	  "IKE current SAs"
	    ::= { cpvIKEglobals 1 }

   cpvIKECurrInitSAs OBJECT-TYPE
	    SYNTAX DisplayString
	    ACCESS read-only
	    STATUS mandatory
	    DESCRIPTION
	    	  "IKE current initiated SAs"
	    ::= { cpvIKEglobals 2 }

   cpvIKECurrRespSAs OBJECT-TYPE
	    SYNTAX DisplayString
	    ACCESS read-only
	    STATUS mandatory
	    DESCRIPTION
	    	  "IKE current responded SAs"
	    ::= { cpvIKEglobals 3 }

   cpvIKETotalSAs OBJECT-TYPE
	    SYNTAX DisplayString
	    ACCESS read-only
	    STATUS mandatory
	    DESCRIPTION
	    	  "IKE total SAs"
	    ::= { cpvIKEglobals 4 }

   cpvIKETotalInitSAs OBJECT-TYPE
	    SYNTAX DisplayString
	    ACCESS read-only
	    STATUS mandatory
	    DESCRIPTION
	    	  "IKE total initiated SAs"
	    ::= { cpvIKEglobals 5 }

   cpvIKETotalRespSAs OBJECT-TYPE
	    SYNTAX DisplayString
	    ACCESS read-only
	    STATUS mandatory
	    DESCRIPTION
	    	  "IKE total responded SAs"
	    ::= { cpvIKEglobals 6 }

   cpvIKETotalSAsAttempts OBJECT-TYPE
	    SYNTAX DisplayString
	    ACCESS read-only
	    STATUS mandatory
	    DESCRIPTION
	    	  "IKE total SAs attempts"
	    ::= { cpvIKEglobals 7 }

   cpvIKETotalSAsInitAttempts OBJECT-TYPE
	    SYNTAX DisplayString
	    ACCESS read-only
	    STATUS mandatory
	    DESCRIPTION
	    	  "IKE total SAs initiated attempts"
	    ::= { cpvIKEglobals 8 }

   cpvIKETotalSAsRespAttempts OBJECT-TYPE
	    SYNTAX DisplayString
	    ACCESS read-only
	    STATUS mandatory
	    DESCRIPTION
	    	  "IKE total SAs responded attempts"
	    ::= { cpvIKEglobals 9 }

   cpvIKEMaxConncurSAs OBJECT-TYPE
	    SYNTAX DisplayString
	    ACCESS read-only
	    STATUS mandatory
	    DESCRIPTION
	    	  "IKE max concurrent SAs"
	    ::= { cpvIKEglobals 10 }

   cpvIKEMaxConncurInitSAs OBJECT-TYPE
	    SYNTAX DisplayString
	    ACCESS read-only
	    STATUS mandatory
	    DESCRIPTION
	    	  "IKE max concurrent initiated SAs"
	    ::= { cpvIKEglobals 11 }

   cpvIKEMaxConncurRespSAs OBJECT-TYPE
	    SYNTAX DisplayString
	    ACCESS read-only
	    STATUS mandatory
	    DESCRIPTION
	    	  "IKE max concurrent responded SAs"
	    ::= { cpvIKEglobals 12 }

   cpvIKETotalFailuresInit OBJECT-TYPE
	    SYNTAX DisplayString
	    ACCESS read-only
	    STATUS mandatory
	    DESCRIPTION
	    	  "IKE total failures (initiator errors)"
	    ::= { cpvIKEerrors 1 }

   cpvIKENoResp OBJECT-TYPE
	    SYNTAX DisplayString
	    ACCESS read-only
	    STATUS mandatory
	    DESCRIPTION
	    	  "IKE no response from peer (initiator errors)"
	    ::= { cpvIKEerrors 2 }

   cpvIKETotalFailuresResp OBJECT-TYPE
	    SYNTAX DisplayString
	    ACCESS read-only
	    STATUS mandatory
	    DESCRIPTION
	    	  "IKE total failures (responder errors)"
	    ::= { cpvIKEerrors 3 }

   cpvIPsecNICsNum OBJECT-TYPE
	    SYNTAX INTEGER
	    ACCESS read-only
	    STATUS mandatory
	    DESCRIPTION
	    	  "IPsec NIC: Number of IPsec NIC's"
	    ::= { cpvIPsecNIC 1 }

   cpvIPsecNICTotalDownLoadedSAs OBJECT-TYPE
	    SYNTAX DisplayString
	    ACCESS read-only
	    STATUS mandatory
	    DESCRIPTION
	    	  "IPsec NIC: Total downloaded SA's"
	    ::= { cpvIPsecNIC 2 }

   cpvIPsecNICCurrDownLoadedSAs OBJECT-TYPE
	    SYNTAX DisplayString
	    ACCESS read-only
	    STATUS mandatory
	    DESCRIPTION
	    	  "IPsec NIC: Current downloaded SA's"
	    ::= { cpvIPsecNIC 3 }

   cpvIPsecNICDecrBytes OBJECT-TYPE
	    SYNTAX DisplayString
	    ACCESS read-only
	    STATUS mandatory
	    DESCRIPTION
	    	  "IPsec NIC: Decrypted bytes by NIC"
	    ::= { cpvIPsecNIC 4 }

   cpvIPsecNICEncrBytes OBJECT-TYPE
	    SYNTAX DisplayString
	    ACCESS read-only
	    STATUS mandatory
	    DESCRIPTION
	    	  "IPsec NIC: Encrypted bytes by NIC"
	    ::= { cpvIPsecNIC 5 }

   cpvIPsecNICDecrPackets OBJECT-TYPE
	    SYNTAX DisplayString
	    ACCESS read-only
	    STATUS mandatory
	    DESCRIPTION
	    	  "IPsec NIC: Decrypted packets by NIC"
	    ::= { cpvIPsecNIC 6 }

   cpvIPsecNICEncrPackets OBJECT-TYPE
	    SYNTAX DisplayString
	    ACCESS read-only
	    STATUS mandatory
	    DESCRIPTION
	    	  "IPsec NIC: Encrypted packets by NIC"
	    ::= { cpvIPsecNIC 7 }

   cpvTnlMon OBJECT-TYPE
	    SYNTAX SEQUENCE OF cpvTnlMonEntry
	    ACCESS read-only
	    STATUS optional
	    DESCRIPTION
	    	  "The table of monitored tunnels"
	    ::= { vpn 11 }

   cpvTnlMonEntry OBJECT-TYPE
	    SYNTAX CpvTnlMonEntry
	    ACCESS read-only
	    STATUS mandatory
			INDEX	{ cpvTnlMonAddr }
	    ::= { cpvTnlMon 1 }

   CpvTnlMonEntry ::=
      SEQUENCE {
        cpvTnlMonAddr
          IpAddress,
        cpvTnlMonStatus
          INTEGER,
        cpvTNlMonCurrAddr
          IpAddress
      }

   cpvTnlMonAddr OBJECT-TYPE
	    SYNTAX IpAddress
	    ACCESS read-only
	    STATUS mandatory
	    DESCRIPTION
	    	  "The main IP address of the peer (bogus IP for DAIP)"
	    ::= { cpvTnlMonEntry 1 }

   cpvTnlMonStatus OBJECT-TYPE
	    SYNTAX INTEGER {
				INITIAL	(0),
				UP		(1)
			}
	    ACCESS read-only
	    STATUS mandatory
	    DESCRIPTION
	    	  "The status of the peer"
	    ::= { cpvTnlMonEntry 2 }

   cpvTnlMonCurrAddr OBJECT-TYPE
	    SYNTAX IpAddress
	    ACCESS read-only
	    STATUS mandatory
	    DESCRIPTION
	    	  "The current IP address of the peer (for DAIPs)"
	    ::= { cpvTnlMonEntry 3 }

	 -- the FG status
	 -- Overall statistics and state

	 fgProdName OBJECT-TYPE
	    SYNTAX DisplayString (SIZE (0..255))
	    ACCESS read-only
	    STATUS mandatory
	    DESCRIPTION
	    	  "Product name"
	    ::= { fg 1 }

	 fgVerMajor OBJECT-TYPE
	    SYNTAX INTEGER
	    ACCESS read-only
	    STATUS mandatory
	    DESCRIPTION
	    	  "Major version"
	    ::= { fg 2 }

	 fgVerMinor OBJECT-TYPE
	    SYNTAX INTEGER
	    ACCESS read-only
	    STATUS mandatory
	    DESCRIPTION
	    	  "Minor version"
	    ::= { fg 3 }

	 fgVersionString OBJECT-TYPE
	    SYNTAX DisplayString (SIZE (0..255))
	    ACCESS read-only
	    STATUS mandatory
	    DESCRIPTION
	    	  "Version string"
	    ::= { fg 4 }

	 fgModuleKernelBuild OBJECT-TYPE
	    SYNTAX INTEGER
	    ACCESS read-only
	    STATUS mandatory
	    DESCRIPTION
	    	  "Kernel build"
	    ::= { fg 5 }

	 fgStrPolicyName OBJECT-TYPE
	    SYNTAX DisplayString (SIZE (0..255))
	    ACCESS read-only
	    STATUS mandatory
	    DESCRIPTION
	    	  "Policy name"
	    ::= { fg 6 }

	 fgInstallTime OBJECT-TYPE
	    SYNTAX DisplayString (SIZE (0..255))
	    ACCESS read-only
	    STATUS mandatory
	    DESCRIPTION
	    	  "Install time"
	    ::= { fg 7 }

	 fgNumInterfaces OBJECT-TYPE
	    SYNTAX DisplayString (SIZE (0..255))
	    ACCESS read-only
	    STATUS mandatory
	    DESCRIPTION
	    	  "Interfaces num"
	    ::= { fg 8 }

	 fgIfTable OBJECT-TYPE
	    SYNTAX SEQUENCE OF FgIfEntry
	    ACCESS not-accessible
	    STATUS mandatory
	     ::= { fg 9 }

	 fgIfEntry OBJECT-TYPE
	 		SYNTAX FgIfEntry
	 		ACCESS not-accessible
	 		STATUS mandatory
	 		INDEX  { fgIfIndex }
	 		::= { fgIfTable 1 }

   FgIfEntry ::=
   		SEQUENCE {
   			fgIfIndex
		     	INTEGER,
		    fgIfName
		    	DisplayString,
		    fgPolicyName
		    	DisplayString,
		    fgRateLimitIn
		     	INTEGER,
		    fgRateLimitOut
		     	INTEGER,
		    fgAvrRateIn
		     	INTEGER,
        fgAvrRateOut
         	INTEGER,
        fgRetransPcktsIn
     		 	INTEGER,
	      fgRetransPcktsOut
	       	INTEGER,
	      fgPendPcktsIn
	       	INTEGER,
	      fgPendPcktsOut
	       	INTEGER,
	      fgPendBytesIn
	       	INTEGER,
	      fgPendBytesOut
	       	INTEGER,
	      fgNumConnIn
	       	INTEGER,
	      fgNumConnOut
	       	INTEGER
	     }

	 fgIfIndex OBJECT-TYPE
       SYNTAX INTEGER
       ACCESS read-only
       STATUS mandatory
       ::= { fgIfEntry 1 }

   fgIfName OBJECT-TYPE
       SYNTAX DisplayString
       ACCESS read-only
       STATUS mandatory
       ::= { fgIfEntry 2 }

   fgPolicyName OBJECT-TYPE
       SYNTAX DisplayString
       ACCESS read-only
       STATUS mandatory
       ::= { fgIfEntry 3 }


   fgRateLimitIn OBJECT-TYPE
       SYNTAX INTEGER
       ACCESS read-only
       STATUS mandatory
       ::= { fgIfEntry 4 }

   fgRateLimitOut OBJECT-TYPE
       SYNTAX INTEGER
       ACCESS read-only
       STATUS mandatory
       ::= { fgIfEntry 5 }

   fgAvrRateIn OBJECT-TYPE
       SYNTAX INTEGER
       ACCESS read-only
       STATUS mandatory
       ::= { fgIfEntry 6 }

   fgAvrRateOut OBJECT-TYPE
       SYNTAX INTEGER
       ACCESS read-only
       STATUS mandatory
       ::= { fgIfEntry 7 }

   fgRetransPcktsIn OBJECT-TYPE
       SYNTAX INTEGER
       ACCESS read-only
       STATUS mandatory
       ::= { fgIfEntry 8 }

   fgRetransPcktsOut OBJECT-TYPE
       SYNTAX INTEGER
       ACCESS read-only
       STATUS mandatory
       ::= { fgIfEntry 9 }

   fgPendPcktsIn OBJECT-TYPE
       SYNTAX INTEGER
       ACCESS read-only
       STATUS mandatory
       ::= { fgIfEntry 10 }

   fgPendPcktsOut OBJECT-TYPE
       SYNTAX INTEGER
       ACCESS read-only
       STATUS mandatory
       ::= { fgIfEntry 11 }

   fgPendBytesIn OBJECT-TYPE
       SYNTAX INTEGER
       ACCESS read-only
       STATUS mandatory
       ::= { fgIfEntry 12 }

   fgPendBytesOut OBJECT-TYPE
       SYNTAX INTEGER
       ACCESS read-only
       STATUS mandatory
       ::= { fgIfEntry 13 }

   fgNumConnIn OBJECT-TYPE
       SYNTAX INTEGER
       ACCESS read-only
       STATUS mandatory
       ::= { fgIfEntry 14 }

   fgNumConnOut OBJECT-TYPE
       SYNTAX INTEGER
       ACCESS read-only
       STATUS mandatory
       ::= { fgIfEntry 15 }

	 -- the HA status
	 -- Overall statistics and state

	 haProdName OBJECT-TYPE
	 		 SYNTAX DisplayString (SIZE (0..255))
			 ACCESS read-only
			 STATUS mandatory
			 DESCRIPTION
					 "Product name"
			 ::= { ha 1 }

	 haInstalled OBJECT-TYPE
	 		 SYNTAX INTEGER
			 ACCESS read-only
			 STATUS mandatory
			 DESCRIPTION
					 "HA installed"
			 ::= { ha 2 }

   haVerMajor OBJECT-TYPE
	 		 SYNTAX INTEGER
			 ACCESS read-only
			 STATUS mandatory
			 DESCRIPTION
					 "Major version"
			 ::= { ha 3 }

	 haVerMinor OBJECT-TYPE
	 		 SYNTAX INTEGER
			 ACCESS read-only
			 STATUS mandatory
			 DESCRIPTION
					 "Minor version"
			 ::= { ha 4 }

	 haStarted OBJECT-TYPE
	 		 SYNTAX DisplayString (SIZE (0..255))
			 ACCESS read-only
			 STATUS mandatory
			 DESCRIPTION
					 "HA started"
			 ::= { ha 5 }

	 haState OBJECT-TYPE
	 		 SYNTAX DisplayString (SIZE (0..255))
			 ACCESS read-only
			 STATUS mandatory
			 DESCRIPTION
					 "HA state"
			 ::= { ha 6 }

	 haBlockState OBJECT-TYPE
	 		 SYNTAX DisplayString (SIZE (0..255))
			 ACCESS read-only
			 STATUS mandatory
			 DESCRIPTION
					 "HA blocking state"
			 ::= { ha 7 }

	 haIdentifier OBJECT-TYPE
	 		 SYNTAX INTEGER
			 ACCESS read-only
			 STATUS mandatory
			 DESCRIPTION
					 "HA identifier"
			 ::= { ha 8 }

	 haProtoVersion OBJECT-TYPE
	 		 SYNTAX INTEGER
			 ACCESS read-only
			 STATUS mandatory
			 DESCRIPTION
					 "HA protocol version"
			 ::= { ha 10 }

	 haWorkMode OBJECT-TYPE
	 		 SYNTAX DisplayString (SIZE (0..255))
			 ACCESS read-only
			 STATUS mandatory
			 DESCRIPTION
					 "Working mode"
			 ::= { ha 11 }

	 haVersionSting OBJECT-TYPE
	 		 SYNTAX DisplayString (SIZE (0..255))
			 ACCESS read-only
			 STATUS mandatory
			 DESCRIPTION
					 "Version string"
			 ::= { ha 14 }

	 haStatCode OBJECT-TYPE
	 		 SYNTAX INTEGER
			 ACCESS read-only
			 STATUS mandatory
			 DESCRIPTION
					 "Status code"
			 ::= { ha 101 }

	 haStatShort OBJECT-TYPE
	 		 SYNTAX DisplayString (SIZE (0..255))
			 ACCESS read-only
			 STATUS mandatory
			 DESCRIPTION
					 "Status short"
			 ::= { ha 102 }

	 haStatLong OBJECT-TYPE
	 		 SYNTAX DisplayString (SIZE (0..255))
			 ACCESS read-only
			 STATUS mandatory
			 DESCRIPTION
					 "Status long"
			 ::= { ha 103 }

	 haServicePack OBJECT-TYPE
	 		 SYNTAX INTEGER
			 ACCESS read-only
			 STATUS mandatory
			 DESCRIPTION
					 "Service pack"
			 ::= { ha 999 }

	 haIfTable OBJECT-TYPE
	    SYNTAX SEQUENCE OF HaIfEntry
	    ACCESS not-accessible
	    STATUS mandatory
	     ::= { ha 12 }

	 haIfEntry OBJECT-TYPE
	 		SYNTAX HaIfEntry
	 		ACCESS not-accessible
	 		STATUS mandatory
	 		INDEX  { haIfIndex }
	 		::= { haIfTable 1 }

   HaIfEntry ::=
   		SEQUENCE {
   			haIfIndex
		     	INTEGER,
		    haIfName
		    	DisplayString,
		    haIP
		     	INTEGER,
		    haStatus
		     	DisplayString,
		    haVerified
		     	INTEGER,
        haTrusted
         	INTEGER,
        haShared
     		 	INTEGER
	     }

	 haIfIndex OBJECT-TYPE
       SYNTAX INTEGER
       ACCESS read-only
       STATUS mandatory
       ::= { haIfEntry 1 }

   haIfName OBJECT-TYPE
       SYNTAX DisplayString
       ACCESS read-only
       STATUS mandatory
       ::= { haIfEntry 2 }

   haIP OBJECT-TYPE
       SYNTAX INTEGER
       ACCESS read-only
       STATUS mandatory
       ::= { haIfEntry 3 }

   haStatus OBJECT-TYPE
       SYNTAX DisplayString
       ACCESS read-only
       STATUS mandatory
       ::= { haIfEntry 4 }

   haVerified OBJECT-TYPE
       SYNTAX INTEGER
       ACCESS read-only
       STATUS mandatory
       ::= { haIfEntry 5 }

   haTrusted OBJECT-TYPE
       SYNTAX INTEGER
       ACCESS read-only
       STATUS mandatory
       ::= { haIfEntry 6 }

   haShared OBJECT-TYPE
       SYNTAX INTEGER
       ACCESS read-only
       STATUS mandatory
       ::= { haIfEntry 7 }


	 haProblemTable OBJECT-TYPE
	    SYNTAX SEQUENCE OF HaProblemEntry
	    ACCESS not-accessible
	    STATUS mandatory
	     ::= { ha 13 }

	 haProblemEntry OBJECT-TYPE
	 		SYNTAX HaProblemEntry
	 		ACCESS not-accessible
	 		STATUS mandatory
	 		INDEX  { haIfIndex }
	 		::= { haProblemTable 1 }

   HaProblemEntry ::=
   		SEQUENCE {
   			haProblemIndex
		     	INTEGER,
		    haProblemName
		    	DisplayString,
		    haProblemStatus
		     	DisplayString,
		    haProblemPriority
		     	INTEGER,
        haProblemVerified
         	INTEGER,
        haProblemDescr
     		 	DisplayString
	     }

	 haProblemIndex OBJECT-TYPE
       SYNTAX INTEGER
       ACCESS read-only
       STATUS mandatory
       ::= { haProblemEntry 1 }

   haProblemName OBJECT-TYPE
       SYNTAX DisplayString
       ACCESS read-only
       STATUS mandatory
       ::= { haProblemEntry 2 }

   haProblemStatus OBJECT-TYPE
       SYNTAX DisplayString
       ACCESS read-only
       STATUS mandatory
       ::= { haProblemEntry 3 }

   haProblemPriority OBJECT-TYPE
       SYNTAX INTEGER
       ACCESS read-only
       STATUS mandatory
       ::= { haProblemEntry 4 }

   haProblemVerified OBJECT-TYPE
       SYNTAX INTEGER
       ACCESS read-only
       STATUS mandatory
       ::= { haProblemEntry 5 }

   haProblemDescr OBJECT-TYPE
       SYNTAX DisplayString
       ACCESS read-only
       STATUS mandatory
       ::= { haProblemEntry 6 }

	 -- the SVN status
	 -- Overall statistics and state

   svnInfo    OBJECT IDENTIFIER ::= { svn 4 }
	 svnOSInfo   OBJECT IDENTIFIER ::= { svn 5 }
	 svnPerf    OBJECT IDENTIFIER ::= { svn 7 }
	 svnMem     OBJECT IDENTIFIER ::= { svnPerf 1 }
	 svnProc    OBJECT IDENTIFIER ::= { svnPerf 2 }
	 svnDisk    OBJECT IDENTIFIER ::= { svnPerf 3 }
	 svnMem64    OBJECT IDENTIFIER ::= { svnPerf 4 }

   svnProdName OBJECT-TYPE
	 		 SYNTAX DisplayString (SIZE (0..255))
			 ACCESS read-only
			 STATUS mandatory
			 DESCRIPTION
	    	  "Product name"
	    ::= { svn 1 }

   svnProdVerMajor OBJECT-TYPE
	 		 SYNTAX INTEGER
			 ACCESS read-only
			 STATUS mandatory
			 DESCRIPTION
	    	  "Major version"
	    ::= { svn 2 }

	 svnProdVerMinor OBJECT-TYPE
	    SYNTAX INTEGER
	    ACCESS read-only
	    STATUS mandatory
	    DESCRIPTION
	    	  "Minor version"
	    ::= { svn 3 }

	 svnVersion OBJECT-TYPE
	 		 SYNTAX DisplayString (SIZE (0..255))
			 ACCESS read-only
			 STATUS mandatory
			 DESCRIPTION
					 "SVN version"
			 ::= { svnInfo 1 }

	 svnBuild OBJECT-TYPE
	 		 SYNTAX INTEGER
			 ACCESS read-only
			 STATUS mandatory
			 DESCRIPTION
					 "SVN build number"
			 ::= { svnInfo 2 }

	 osName OBJECT-TYPE
	 		 SYNTAX DisplayString (SIZE (0..255))
			 ACCESS read-only
			 STATUS mandatory
			 DESCRIPTION
					 "OS name"
			 ::= { svnOSInfo 1 }

	 osMajorVer OBJECT-TYPE
	 		 SYNTAX INTEGER
			 ACCESS read-only
			 STATUS mandatory
			 DESCRIPTION
					 "OS Major version"
			 ::= { svnOSInfo 2 }

	 osMinorVer OBJECT-TYPE
	 		 SYNTAX INTEGER
			 ACCESS read-only
			 STATUS mandatory
			 DESCRIPTION
					 "OS minor version"
			 ::= { svnOSInfo 3 }

	 osBuildNum OBJECT-TYPE
	 		 SYNTAX INTEGER
			 ACCESS read-only
			 STATUS optional
			 DESCRIPTION
					 "OS build number"
			 ::= { svnOSInfo 4 }

	 osSPmajor OBJECT-TYPE
	 		 SYNTAX INTEGER
			 ACCESS read-only
			 STATUS optional
			 DESCRIPTION
					 "OS SP major"
			 ::= { svnOSInfo 5 }

	 osSPminor OBJECT-TYPE
	 		 SYNTAX INTEGER
			 ACCESS read-only
			 STATUS optional
			 DESCRIPTION
					 "OS SP minor"
			 ::= { svnOSInfo 6 }

	 osVersionLevel OBJECT-TYPE
	 		 SYNTAX DisplayString (SIZE (0..255))
			 ACCESS read-only
			 STATUS optional
			 DESCRIPTION
					 "OS version level"
			 ::= { svnOSInfo 7 }

	 memTotalVirtual OBJECT-TYPE
			 SYNTAX INTEGER
			 ACCESS read-only
			 STATUS mandatory
			 DESCRIPTION
					 "Total virtual memory (32 bit)
					 NOTE: This 32 bit object has been superseded by a 64 bit object -
					 memTotalVirtual64, which is supported by Check Point SVN FP3 and above. The
					 32 bit object is still supported, but it is recommended to work with the new
					 64 bit object (avoid receiving erroneous values from 64 bit machines)."
			 ::= { svnMem 1 }

	 memActiveVirtual OBJECT-TYPE
			 SYNTAX INTEGER
			 ACCESS read-only
			 STATUS mandatory
			 DESCRIPTION
					 "Active virtual memory (32 bit)
					 NOTE: This 32 bit object has been superseded by a 64 bit object -
					 memActiveVirtual64, which is supported by Check Point SVN FP3 and above. The
					 32 bit object is still supported, but it is recommended to work with the new
					 64 bit object (avoid receiving erroneous values from 64 bit machines)."
			 ::= { svnMem 2 }

	 memTotalReal OBJECT-TYPE
			 SYNTAX INTEGER
			 ACCESS read-only
			 STATUS mandatory
			 DESCRIPTION
					 "Total real memory (32 bit)
					 NOTE: This 32 bit object has been superseded by a 64 bit object -
					 memTotalReal64, which is supported by Check Point SVN FP3 and above. The
					 32 bit object is still supported, but it is recommended to work with the new
					 64 bit object (avoid receiving erroneous values from 64 bit machines)."
			 ::= { svnMem 3 }

	 memActiveReal OBJECT-TYPE
			 SYNTAX INTEGER
			 ACCESS read-only
			 STATUS optional
			 DESCRIPTION
					 "Active real memory (32 bit)
					 NOTE: This 32 bit object has been superseded by a 64 bit object -
					 memActiveReal64, which is supported by Check Point SVN FP3 and above. The
					 32 bit object is still supported, but it is recommended to work with the new
					 64 bit object (avoid receiving erroneous values from 64 bit machines)."
			 ::= { svnMem 4 }

	 memFreeReal OBJECT-TYPE
			 SYNTAX INTEGER
			 ACCESS read-only
			 STATUS mandatory
			 DESCRIPTION
					 "Free real memory (32 bit)
					 NOTE: This 32 bit object has been superseded by a 64 bit object -
					 memFreeReal64, which is supported by Check Point SVN FP3 and above. The
					 32 bit object is still supported, but it is recommended to work with the new
					 64 bit object (avoid receiving erroneous values from 64 bit machines)."
			 ::= { svnMem 5 }

	 memSwapsSec OBJECT-TYPE
			 SYNTAX INTEGER
			 ACCESS read-only
			 STATUS optional
			 DESCRIPTION
					 "Memory swaped pages/sec (32 bit)
					 NOTE: This 32 bit object has been superseded by a 64 bit object -
					 memSwapsSec64, which is supported by Check Point SVN FP3 and above. The
					 32 bit object is still supported, but it is recommended to work with the new
					 64 bit object (avoid receiving erroneous values from 64 bit machines)."
			 ::= { svnMem 6 }

	 memDiskTransfers OBJECT-TYPE
			 SYNTAX INTEGER
			 ACCESS read-only
			 STATUS optional
			 DESCRIPTION
					 "Memory to Disk transfers/sec (32 bit)
					 NOTE: This 32 bit object has been superseded by a 64 bit object -
					 memDiskTransfers64, which is supported by Check Point SVN FP3 and above. The
					 32 bit object is still supported, but it is recommended to work with the new
					 64 bit object (avoid receiving erroneous values from 64 bit machines)."
			 ::= { svnMem 7 }

	 procUsrTime OBJECT-TYPE
			 SYNTAX INTEGER
			 ACCESS read-only
			 STATUS mandatory
			 DESCRIPTION
					 "Processor user time"
			 ::= { svnProc 1 }

	 procSysTime OBJECT-TYPE
			 SYNTAX INTEGER
			 ACCESS read-only
			 STATUS mandatory
			 DESCRIPTION
					 "Processor system time"
			 ::= { svnProc 2 }

	 procIdleTime OBJECT-TYPE
			 SYNTAX INTEGER
			 ACCESS read-only
			 STATUS mandatory
			 DESCRIPTION
					 "Processor idle time"
			 ::= { svnProc 3 }

	 procUsage OBJECT-TYPE
			 SYNTAX INTEGER
			 ACCESS read-only
			 STATUS mandatory
			 DESCRIPTION
					 "Processor usage"
			 ::= { svnProc 4 }

	 procQueue OBJECT-TYPE
			 SYNTAX INTEGER
			 ACCESS read-only
			 STATUS optional
			 DESCRIPTION
					 "Processor queue length"
			 ::= { svnProc 5 }

	 procInterrupts OBJECT-TYPE
			 SYNTAX INTEGER
			 ACCESS read-only
			 STATUS optional
			 DESCRIPTION
					 "Processor interrupts/sec"
			 ::= { svnProc 6 }

	 procNum OBJECT-TYPE
			 SYNTAX INTEGER
			 ACCESS read-only
			 STATUS mandatory
			 DESCRIPTION
					 "Number of processors"
			 ::= { svnProc 7 }

	 diskTime OBJECT-TYPE
       SYNTAX INTEGER
			 ACCESS read-only
			 STATUS optional
			 DESCRIPTION
					 "Time the disk is performing io requests"
			 ::= { svnDisk 1 }

	 diskQueue OBJECT-TYPE
       SYNTAX INTEGER
			 ACCESS read-only
			 STATUS optional
			 DESCRIPTION
					 "Disk requests queue length"
			 ::= { svnDisk 2 }

	 diskPercent OBJECT-TYPE
       SYNTAX INTEGER
			 ACCESS read-only
			 STATUS mandatory
			 DESCRIPTION
					 "Percent of free space"
			 ::= { svnDisk 3 }

	 diskFreeTotal OBJECT-TYPE
       SYNTAX DisplayString (SIZE (0..255))
			 ACCESS read-only
			 STATUS mandatory
			 DESCRIPTION
					 "Disk total free space"
			 ::= { svnDisk 4 }

	 diskFreeAvail OBJECT-TYPE
       SYNTAX DisplayString (SIZE (0..255))
			 ACCESS read-only
			 STATUS mandatory
			 DESCRIPTION
					 "Disk available free space"
			 ::= { svnDisk 5 }

	 diskTotal OBJECT-TYPE
       SYNTAX DisplayString (SIZE (0..255))
			 ACCESS read-only
			 STATUS mandatory
			 DESCRIPTION
					 "Disk total space"
			 ::= { svnDisk 6 }

	 memTotalVirtual64 OBJECT-TYPE
			 SYNTAX DisplayString (SIZE (0..255))
			 ACCESS read-only
			 STATUS optional
			 DESCRIPTION
					 "Total virtual memory"
			 ::= { svnMem64 1 }

	 memActiveVirtual64 OBJECT-TYPE
			 SYNTAX DisplayString (SIZE (0..255))
			 ACCESS read-only
			 STATUS optional
			 DESCRIPTION
					 "Active virtual memory"
			 ::= { svnMem64 2 }

	 memTotalReal64 OBJECT-TYPE
			 SYNTAX DisplayString (SIZE (0..255))
			 ACCESS read-only
			 STATUS optional
			 DESCRIPTION
					 "Total real memory"
			 ::= { svnMem64 3 }

	 memActiveReal64 OBJECT-TYPE
			 SYNTAX DisplayString (SIZE (0..255))
			 ACCESS read-only
			 STATUS optional
			 DESCRIPTION
					 "Active real memory"
			 ::= { svnMem64 4 }

	 memFreeReal64 OBJECT-TYPE
			 SYNTAX DisplayString (SIZE (0..255))
			 ACCESS read-only
			 STATUS optional
			 DESCRIPTION
					 "Free real memory"
			 ::= { svnMem64 5 }

	 memSwapsSec64 OBJECT-TYPE
			 SYNTAX INTEGER
			 ACCESS read-only
			 STATUS optional
			 DESCRIPTION
					 "Memory swaped pages/sec"
			 ::= { svnMem64 6 }

	 memDiskTransfers64 OBJECT-TYPE
			 SYNTAX INTEGER
			 ACCESS read-only
			 STATUS optional
			 DESCRIPTION
					 "Memory to Disk transfers/sec"
			 ::= { svnMem64 7 }

	 routingTable OBJECT-TYPE
	     SYNTAX SEQUENCE OF RoutingEntry
			 ACCESS not-accessible
			 STATUS mandatory
			 ::= { svn 6 }

	 routingEntry OBJECT-TYPE
	     SYNTAX RoutingEntry
			 ACCESS not-accessible
			 STATUS mandatory
			 INDEX  { routingIndex }
			 ::= { routingTable 1 }

	 RoutingEntry ::=
	     SEQUENCE {
				routingIndex
				   INTEGER,
				routingDest
				   IpAddress,
				routingMask
					 routingDest,
				routingGatweway
				   routingDest,
				routingIntrfName
				   DisplayString
			 }

   routingIndex OBJECT-TYPE
       SYNTAX INTEGER
       ACCESS read-only
       STATUS mandatory
       ::= { routingEntry 1 }

   routingDest OBJECT-TYPE
   		 SYNTAX IpAddress
       ACCESS read-only
       STATUS mandatory
       ::= { routingEntry 2 }

   routingMask OBJECT-TYPE
   		 SYNTAX routingDest
       ACCESS read-only
       STATUS mandatory
       ::= { routingEntry 3 }

   routingGatweway OBJECT-TYPE
   		 SYNTAX routingDest
       ACCESS read-only
       STATUS mandatory
       ::= { routingEntry 4 }

   routingIntrfName OBJECT-TYPE
   		 SYNTAX DisplayString
       ACCESS read-only
       STATUS mandatory
       ::= { routingEntry 5 }

   svnStatCode OBJECT-TYPE
   		 SYNTAX INTEGER
   		 ACCESS read-only
   		 STATUS mandatory
	     DESCRIPTION
	    	  "Status code"
   		 ::= { svn 101 }

   svnStatShortDescr OBJECT-TYPE
   		 SYNTAX DisplayString (SIZE (0..255))
   		 ACCESS read-only
   		 STATUS mandatory
	     DESCRIPTION
	    	  "Status short description"
   		 ::= { svn 102 }

   svnStatLongDescr OBJECT-TYPE
   		 SYNTAX DisplayString (SIZE (0..255))
   		 ACCESS read-only
   		 STATUS mandatory
	     DESCRIPTION
	    	  "Status long description"
   		 ::= { svn 103 }

   svnServicePack OBJECT-TYPE
   		 SYNTAX INTEGER
   		 ACCESS read-only
   		 STATUS mandatory
	     DESCRIPTION
	    	  "SVN service pack"
   		 ::= { svn 999 }

   -- the Managment status
	 -- Overall statistics and state

   mgProdName OBJECT-TYPE
   		 SYNTAX DisplayString (SIZE (0..255))
   		 ACCESS read-only
   		 STATUS mandatory
	     DESCRIPTION
	    	  "Product name"
   		 ::= { mngmt 1 }

   mgVerMajor OBJECT-TYPE
   		 SYNTAX INTEGER
   		 ACCESS read-only
   		 STATUS mandatory
	     DESCRIPTION
	    	  "Major version"
   		 ::= { mngmt 2 }

   mgVerMinor OBJECT-TYPE
   		 SYNTAX INTEGER
   		 ACCESS read-only
   		 STATUS mandatory
	     DESCRIPTION
	    	  "Minor version"
   		 ::= { mngmt 3 }

   mgBuildNumber OBJECT-TYPE
   		 SYNTAX INTEGER
   		 ACCESS read-only
   		 STATUS mandatory
	     DESCRIPTION
	    	  "Build number"
   		 ::= { mngmt 4 }

   mgActiveStatus OBJECT-TYPE
   		 SYNTAX DisplayString
   		 ACCESS read-only
   		 STATUS mandatory
	     DESCRIPTION
	    	  "Active status"
   		 ::= { mngmt 5 }

   mgFwmIsAlive OBJECT-TYPE
   		 SYNTAX INTEGER
   		 ACCESS read-only
   		 STATUS mandatory
	     DESCRIPTION
	    	  "Managment is alive"
   		 ::= { mngmt 6 }

	 mgConnectedClientsTable OBJECT-TYPE
       SYNTAX SEQUENCE OF MgConnectedClientsEntry
			 ACCESS not-accessible
			 STATUS mandatory
			 ::= { mngmt 7 }

	 mgConnectedClientsEntry OBJECT-TYPE
	     SYNTAX MgConnectedClientsEntry
			 ACCESS not-accessible
			 STATUS mandatory
			 INDEX  { mgIndex }
			 ::= { mgConnectedClientsTable 1 }

	 MgConnectedClientsEntry ::=
	     SEQUENCE {
				mgIndex
				   INTEGER,
				mgClientName
				   DisplayString,
				mgClientHost
					 DisplayString,
				mgClientDbLock
				   DisplayString,
				mgApplicationType
				   DisplayString
			 }

   mgIndex OBJECT-TYPE
       SYNTAX INTEGER
       ACCESS read-only
       STATUS mandatory
       ::= { mgConnectedClientsEntry 1 }

   mgClientName OBJECT-TYPE
       SYNTAX DisplayString
       ACCESS read-only
       STATUS mandatory
       ::= { mgConnectedClientsEntry 2 }

   mgClientHost OBJECT-TYPE
       SYNTAX DisplayString
       ACCESS read-only
       STATUS mandatory
       ::= { mgConnectedClientsEntry 3 }

   mgClientDbLock OBJECT-TYPE
       SYNTAX DisplayString
       ACCESS read-only
       STATUS mandatory
       ::= { mgConnectedClientsEntry 4 }

   mgApplicationType OBJECT-TYPE
       SYNTAX DisplayString
       ACCESS read-only
       STATUS mandatory
       ::= { mgConnectedClientsEntry 5 }

   mgStatCode OBJECT-TYPE
   		 SYNTAX INTEGER
   		 ACCESS read-only
   		 STATUS mandatory
	     DESCRIPTION
	    	  "Status code"
   		 ::= { mngmt 101 }

   mgStatShortDescr OBJECT-TYPE
   		 SYNTAX DisplayString (SIZE (0..255))
   		 ACCESS read-only
   		 STATUS mandatory
	     DESCRIPTION
	    	  "Status short description"
   		 ::= { mngmt 102 }

   mgStatLongDescr OBJECT-TYPE
   		 SYNTAX DisplayString (SIZE (0..255))
   		 ACCESS read-only
   		 STATUS mandatory
	     DESCRIPTION
	    	  "Status long description"
   		 ::= { mngmt 103 }

   -- the WAM Status
	 -- Overall statistics and state

   wamPluginPerformance  OBJECT IDENTIFIER ::= { wam 6 }
	 wamPolicy       OBJECT IDENTIFIER ::= { wam 7 }
	 wamUagQueries     OBJECT IDENTIFIER ::= { wam 8 }
	 wamGlobalPerformance  OBJECT IDENTIFIER ::= { wam 9 }

   wamProdName OBJECT-TYPE
   		 SYNTAX DisplayString (SIZE (0..255))
   		 ACCESS read-only
   		 STATUS mandatory
	     DESCRIPTION
	    	  "Product name"
   		 ::= { wam 1 }

   wamVerMajor OBJECT-TYPE
   		 SYNTAX INTEGER
   		 ACCESS read-only
   		 STATUS mandatory
	     DESCRIPTION
	    	  "Major version"
   		 ::= { wam 2 }

   wamVerMinor OBJECT-TYPE
   		 SYNTAX INTEGER
   		 ACCESS read-only
   		 STATUS mandatory
	     DESCRIPTION
	    	  "Minor version"
   		 ::= { wam 3 }

   wamState OBJECT-TYPE
   		 SYNTAX DisplayString (SIZE (0..255))
   		 ACCESS read-only
   		 STATUS mandatory
	     DESCRIPTION
	    	  "WAM state"
   		 ::= { wam 4 }

   wamName OBJECT-TYPE
   		 SYNTAX DisplayString (SIZE (0..255))
   		 ACCESS read-only
   		 STATUS mandatory
	     DESCRIPTION
	    	  "WAM name"
   		 ::= { wam 5 }

   wamStatCode OBJECT-TYPE
   		 SYNTAX INTEGER
   		 ACCESS read-only
   		 STATUS mandatory
	     DESCRIPTION
	    	  "WAM status code"
   		 ::= { wam 101 }

   wamStatShortDescr OBJECT-TYPE
   		 SYNTAX DisplayString (SIZE (0..255))
   		 ACCESS read-only
   		 STATUS mandatory
	     DESCRIPTION
	    	  "WAM status short description"
   		 ::= { wam 102 }

   wamStatLongDescr OBJECT-TYPE
   		 SYNTAX DisplayString (SIZE (0..255))
   		 ACCESS read-only
   		 STATUS mandatory
	     DESCRIPTION
	    	  "WAM status full description"
   		 ::= { wam 103 }

   wamAcceptReq OBJECT-TYPE
   		 SYNTAX INTEGER
   		 ACCESS read-only
   		 STATUS mandatory
	     DESCRIPTION
	    	  "Plugin accepted requests"
   		 ::= { wamPluginPerformance 1 }

   wamRejectReq OBJECT-TYPE
   		 SYNTAX INTEGER
   		 ACCESS read-only
   		 STATUS mandatory
	     DESCRIPTION
	    	  "Plugin rejected requests"
   		 ::= { wamPluginPerformance 2 }

   wamPolicyName OBJECT-TYPE
   		 SYNTAX DisplayString (SIZE (0..255))
   		 ACCESS read-only
   		 STATUS mandatory
	     DESCRIPTION
	    	  "Policy name"
   		 ::= { wamPolicy 1 }

   wamPolicyUpdate OBJECT-TYPE
   		 SYNTAX DisplayString (SIZE (0..255))
   		 ACCESS read-only
   		 STATUS mandatory
	     DESCRIPTION
	    	  "Last update time"
   		 ::= { wamPolicy 2 }

   wamUagHost OBJECT-TYPE
   		 SYNTAX DisplayString (SIZE (0..255))
   		 ACCESS read-only
   		 STATUS mandatory
	     DESCRIPTION
	    	  "UAG host name"
   		 ::= { wamUagQueries 1 }

   wamUagIp OBJECT-TYPE
   		 SYNTAX INTEGER
   		 ACCESS read-only
   		 STATUS mandatory
	     DESCRIPTION
	    	  "UAG IP address"
   		 ::= { wamUagQueries 2 }

   wamUagPort OBJECT-TYPE
   		 SYNTAX INTEGER
   		 ACCESS read-only
   		 STATUS mandatory
	     DESCRIPTION
	    	  "UAG port"
   		 ::= { wamUagQueries 3 }

   wamUagNoQueries OBJECT-TYPE
   		 SYNTAX INTEGER
   		 ACCESS read-only
   		 STATUS mandatory
	     DESCRIPTION
	    	  "UAG no. of queries"
   		 ::= { wamUagQueries 4 }

   wamUagLastQuery OBJECT-TYPE
   		 SYNTAX DisplayString (SIZE (0..255))
   		 ACCESS read-only
   		 STATUS mandatory
	     DESCRIPTION
	    	  "UAG last query time"
   		 ::= { wamUagQueries 5 }

   wamOpenSessions OBJECT-TYPE
   		 SYNTAX INTEGER
   		 ACCESS read-only
   		 STATUS mandatory
	     DESCRIPTION
	    	  "Open sessions"
   		 ::= { wamGlobalPerformance 1 }

   wamLastSession OBJECT-TYPE
   		 SYNTAX DisplayString (SIZE (0..255))
   		 ACCESS read-only
   		 STATUS mandatory
	     DESCRIPTION
	    	  "Last open session time"
   		 ::= { wamGlobalPerformance 2 }


   -- the Desktop Policy Server Status
	 -- Overall statistics and state

   dtpsProdName OBJECT-TYPE
   		 SYNTAX DisplayString (SIZE (0..255))
   		 ACCESS read-only
   		 STATUS mandatory
	     DESCRIPTION
	    	  "Product name"
   		 ::= { dtps 1 }

   dtpsVerMajor OBJECT-TYPE
   		 SYNTAX INTEGER
   		 ACCESS read-only
   		 STATUS mandatory
	     DESCRIPTION
	    	  "Major version"
   		 ::= { dtps 2 }

   dtpsVerMinor OBJECT-TYPE
   		 SYNTAX INTEGER
   		 ACCESS read-only
   		 STATUS mandatory
	     DESCRIPTION
	    	  "Minor version"
   		 ::= { dtps 3 }

   dtpsLicensedUsers OBJECT-TYPE
   		 SYNTAX INTEGER
   		 ACCESS read-only
   		 STATUS mandatory
	     DESCRIPTION
	    	  "Licensed users"
   		 ::= { dtps 4 }

   dtpsConnectedUsers OBJECT-TYPE
   		 SYNTAX INTEGER
   		 ACCESS read-only
   		 STATUS mandatory
	     DESCRIPTION
	    	  "Connected users"
   		 ::= { dtps 5 }

   dtpsStatCode OBJECT-TYPE
   		 SYNTAX INTEGER
   		 ACCESS read-only
   		 STATUS mandatory
	     DESCRIPTION
	    	  "Status code"
   		 ::= { dtps 101 }

   dtpsStatShortDescr OBJECT-TYPE
   		 SYNTAX DisplayString (SIZE (0..255))
   		 ACCESS read-only
   		 STATUS mandatory
	     DESCRIPTION
	    	  "Status short description"
   		 ::= { dtps 102 }

   dtpsStatLongDescr OBJECT-TYPE
   		 SYNTAX DisplayString (SIZE (0..255))
   		 ACCESS read-only
   		 STATUS mandatory
	     DESCRIPTION
	    	  "Status long description"
   		 ::= { dtps 103 }

   -- the Log Server Status
	 -- Overall statistics and state

   lsProdName OBJECT-TYPE
   		 SYNTAX DisplayString (SIZE (0..255))
   		 ACCESS read-only
   		 STATUS mandatory
	     DESCRIPTION
	    	  "Product name"
   		 ::= { ls 1 }

   lsVerMajor OBJECT-TYPE
   		 SYNTAX INTEGER
   		 ACCESS read-only
   		 STATUS mandatory
	     DESCRIPTION
	    	  "Major version"
   		 ::= { ls 2 }

   lsVerMinor OBJECT-TYPE
   		 SYNTAX INTEGER
   		 ACCESS read-only
   		 STATUS mandatory
	     DESCRIPTION
	    	  "Minor version"
   		 ::= { ls 3 }

   lsBuildNumber OBJECT-TYPE
   		 SYNTAX INTEGER
   		 ACCESS read-only
   		 STATUS mandatory
	     DESCRIPTION
	    	  "Build number"
   		 ::= { ls 4 }

   lsFwmIsAlive OBJECT-TYPE
   		 SYNTAX INTEGER
   		 ACCESS read-only
   		 STATUS mandatory
	     DESCRIPTION
	    	  "Log Server is alive"
   		 ::= { ls 5 }

   lsStatCode OBJECT-TYPE
   		 SYNTAX INTEGER
   		 ACCESS read-only
   		 STATUS mandatory
	     DESCRIPTION
	    	  "Status code"
   		 ::= { ls 101 }

   lsStatShortDescr OBJECT-TYPE
   		 SYNTAX DisplayString (SIZE (0..255))
   		 ACCESS read-only
   		 STATUS mandatory
	     DESCRIPTION
	    	  "Status short description"
   		 ::= { ls 102 }

   lsStatLongDescr OBJECT-TYPE
   		 SYNTAX DisplayString (SIZE (0..255))
   		 ACCESS read-only
   		 STATUS mandatory
	     DESCRIPTION
	    	  "Status long description"
   		 ::= { ls 103 }

	 lsConnectedClientsTable OBJECT-TYPE
       SYNTAX SEQUENCE OF LSConnectedClientsEntry
			 ACCESS not-accessible
			 STATUS mandatory
			 ::= { ls 7 }

	 lsConnectedClientsEntry OBJECT-TYPE
	     SYNTAX LSConnectedClientsEntry
			 ACCESS not-accessible
			 STATUS mandatory
			 INDEX  { lsIndex }
			 ::= { lsConnectedClientsTable 1 }

	 LSConnectedClientsEntry ::=
	     SEQUENCE {
				lsIndex
				   INTEGER,
				lsClientName
				   DisplayString,
				lsClientHost
					 DisplayString,
				lsClientDbLock
				   DisplayString,
				lsApplicationType
				   DisplayString
			 }

   lsIndex OBJECT-TYPE
       SYNTAX INTEGER
       ACCESS read-only
       STATUS mandatory
       ::= { lsConnectedClientsEntry 1 }

   lsClientName OBJECT-TYPE
       SYNTAX DisplayString
       ACCESS read-only
       STATUS mandatory
       ::= { lsConnectedClientsEntry 2 }

   lsClientHost OBJECT-TYPE
       SYNTAX DisplayString
       ACCESS read-only
       STATUS mandatory
       ::= { lsConnectedClientsEntry 3 }

   lsClientDbLock OBJECT-TYPE
       SYNTAX DisplayString
       ACCESS read-only
       STATUS mandatory
       ::= { lsConnectedClientsEntry 4 }

   lsApplicationType OBJECT-TYPE
       SYNTAX DisplayString
       ACCESS read-only
       STATUS mandatory
       ::= { lsConnectedClientsEntry 5 }


--


END
