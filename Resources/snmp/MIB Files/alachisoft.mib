ALACHISOFT-MIB DEFINITIONS ::= BEGIN

IMPORTS
    enterprises
                FROM RFC1155-SMI
	Integer32, Counter64, OBJECT-TYPE 
				FROM SNMPv2-SMI;		

alachisoft	  OBJECT IDENTIFIER ::= {enterprises 12}
ncache		  OBJECT IDENTIFIER ::= {alachisoft 1}
cache		  OBJECT IDENTIFIER ::= {ncache 1}
client		  OBJECT IDENTIFIER ::= {ncache 2}

-------------Cache Table Counters----------------
cacheTable OBJECT-TYPE
      SYNTAX      SEQUENCE OF CacheEntry
      MAX-ACCESS  not-accessible
      STATUS      current
      DESCRIPTION
              "A list of interface entries.  The number of entries
               is given by the value of ifNumber."
       ::= { cache 1 }
cacheEntry OBJECT-TYPE
     SYNTAX      CacheEntry
     MAX-ACCESS  not-accessible
     STATUS      current
     DESCRIPTION
             "An entry containing management information applicable
             to a particular interface."
     INDEX   { cacheIndex }
     ::= { cacheTable 1 }
	 




CacheEntry ::=
    SEQUENCE {
        cacheIndex                        Integer32 ,
        cacheName                         DisplayString,
		cacheConfigId                     DisplayString,
		clientServerIP                    DisplayString,
		isReplica                         DisplayString,
		additionsPerSecond                   Counter64,
		averageMSecPerAddBulk             Counter64,
		averageMSecPerBridgeOperation     Counter64,
		averageMSecPerCacheOperation      Counter64,
		averageMSecPerFetch               Counter64,
		averageMSecPerFetchBulk           Counter64,
		averageMSecPerInsert              Counter64,
		averageMSecPerInsertBulk          Counter64,
		averageMSecPerRemove              Counter64,
		averageMSecPerRemoveBulk          Counter64,
		cacheSize                         Counter64,
		cacheCount                        Counter64,
		dictionaryCount                   Counter64,
		counterCount                      Counter64,
		counterSize                       Counter64,
		deletesPerSec                     Counter64,
		messageStoreSize                  Counter64,
		messagesCount                     Counter64,
		expirationIndexSize               Counter64,
		expirationsPerSec                 Counter64,
		fetchesPerSec                     Counter64,
		requestsPerSec                    Counter64,
		updatesPerSec                     Counter64,
		averageMSecPerQueryExecution      Counter64,
		averageMSecPerDataSourceUpdate    Counter64,
		averageMSecPerDataSourceWrite     Counter64,
		numberOfClients                   Counter64,
		averageQuerySize                  Counter64,
		averageMSecPerReadThru            Counter64,
		averageMSecPerWriteBehind         Counter64,
		averageMSecWriteThru              Counter64,
		bCastQueueCount                   Counter64,
		bridgeOperationsReceived          Counter64,
		bridgeOperationsReceivedPerSec    Counter64,
		bridgeOperationsSent              Counter64,
		bridgeOperationsSentPerSec        Counter64,
		bridgeQueueCount                  Counter64,
		bridgeQueueSize                   Counter64,
		bytesReceivedPerSec               Counter64,
		bytesSentPerSec                   Counter64,
		cacheLastAccessCount              Counter64,
		clientBytesReceivedPerSec         Counter64,
		clientBytesSentPerSec             Counter64,
		clientRequestsPerSec              Counter64,
		clientResponsesPerSec             Counter64,
		clusterOpsPerSec                  Counter64,
		clusteredOpsRecvedPerSec          Counter64,
		clusteredOperationsSentPerSec     Counter64,
		dataBalancePerSec                 Counter64,
		dataSourceFailedOperationsPerSec  Counter64,
		dataSourceUpdatesPerSec           Counter64,
		dictionarySize                    Counter64,
		dispatchEnterPerSec               Counter64,
		eventQueueCount                   Counter64,
		evictionIndexSize                 Counter64,
		evictionsPerSec                   Counter64,
		generalNotificationsQueueSize     Counter64,
		groupIndexSize                    Counter64,
		hitsRatioPerSec                   Counter64,
		hitsPerSec                        Counter64,
		listCount                         Counter64,
		listSize                          Counter64,
		loggedRequestCount                Counter64,
		mapReduceCombinedPerSec           Counter64,
		mapReduceMappedPerSec             Counter64,
		mapReduceReducedPerSec            Counter64,
		mapReduceRunningTasks             Counter64,
		mapReduceWaitingTasks             Counter64,
		mCastQueueCount                   Counter64,
		messagesDeliveredPerSec           Counter64,
		messagesExpiredPerSec             Counter64,
		messagesPublishedPerSec           Counter64,
		mirrorQueueSize                   Counter64,
		missesPerSec                      Counter64,
		naglingMsgCount                   Counter64,
		queriesPerSec                     Counter64,
		queryIndexSize                    Counter64,
		queueCount                        Counter64,
		queueSize                         Counter64,
		readersCount                      Counter64,
		readThruPerSec                    Counter64,
		requestLogLedgerSize              Counter64,
		requestsLoggedPerSec              Counter64,
		responseQueueCount                Counter64,
		responseQueueSize                 Counter64,
		responseSentPerSec                Counter64,
		responsesPerSec                   Counter64,
		setCount                          Counter64,
		setSize                           Counter64,
		slidingIndexqueuesize             Counter64,
		socketRecvSize                    Counter64,
		socketRecvtime                    Counter64,
		socketSendSize                    Counter64,
		socketSendTime                    Counter64,
		stateTransferPerSec               Counter64,
		tcpDownEnterPerSec                Counter64,
		tcpDownQueueCount                 Counter64,
		tcpUpQueueCount                   Counter64,
		topicsCount                       Counter64,
		writeBehindBatchCount             Counter64,
		writeBehindEvictionsPerSec        Counter64,
		writeBehindFailureRetrycount      Counter64,
		writeBehindQueueCount             Counter64,
		writeBehindPerSec                 Counter64,
		writeThruPerSec                   Counter64,
		totalCacheSize                    Counter64,
		configuredServersCount            Counter64,
		averageMSecPerAdd                 Counter64,
		persistQCount                     Counter64,
		persistQSize                      Counter64,
		dbReadsPerSec                     Counter64,
		dbWritesPerSec                    Counter64,
		averageMsecPerDbRead              Counter64,
		averageMsecPerDbWrite             Counter64,
		lastDbReadTime                    Counter64,
		lastDbWriteTime                   Counter64,
		replicationQueueCount             Counter64,
		indexes                           Counter64,
		liveInstances                     Counter64,
		documents                         Counter64,
		indexSize                         Counter64,
		commits                           Counter64,
		bucketsToSend                     Counter64,
		bucketsToReceive                  Counter64,
		lucene_updatesPerSec              Counter64,
		searchesPerSec                    Counter64,
		additionsPerSec                   Counter64,
		lucene_fetchesPerSec              Counter64,
		lucene_deletesPerSec              Counter64,
		lucene_stateTransferPerSec        Counter64,
		avgMsecPerSearch                  Counter64,
		avgMsecPerFetch                   Counter64,
		avgMsecPerAdd                     Counter64,
		avgMsecPerUpdate                  Counter64,
		avgMsecPerDelete                  Counter64,
		lucene_requestsPerSec             Counter64
		
		
    }
cacheIndex OBJECT-TYPE
    SYNTAX      Integer32 
    MAX-ACCESS  read-only
    STATUS      current
    DESCRIPTION
            "A unique value, greater than zero, for each cache."
    ::= { cacheEntry 1 }
	
cacheName OBJECT-TYPE
	SYNTAX DisplayString
	ACCESS read-only
	STATUS mandatory
	DESCRIPTION
		"Name of the cache."
	::= {cacheEntry 2}
	
cacheConfigId OBJECT-TYPE
	SYNTAX DisplayString
	ACCESS read-only
	STATUS mandatory
	DESCRIPTION
		"Configuration Id of cache."
	::= {cacheEntry 3}
	
clientServerIP OBJECT-TYPE
	SYNTAX DisplayString
	ACCESS read-only
	STATUS mandatory
	DESCRIPTION
		"IP Adress of the server node."
	::= {cacheEntry 4}
	
isReplica OBJECT-TYPE
	SYNTAX DisplayString
	ACCESS read-only
	STATUS mandatory
	DESCRIPTION
		"Specifies whether server node is replica."
	::= {cacheEntry 5}
	
additionsPerSecond OBJECT-TYPE
	SYNTAX Counter64
	ACCESS read-only
	STATUS mandatory
	DESCRIPTION
		"Number of Add operations per second."
	::= {cacheEntry 6}
	
averageMSecPerAddBulk OBJECT-TYPE
SYNTAX Counter64
ACCESS read-only
STATUS mandatory
DESCRIPTION
	"Average time in microseconds (us), taken to complete bulk add operation."
::= {cacheEntry 7}

averageMSecPerBridgeOperation OBJECT-TYPE
SYNTAX Counter64
ACCESS read-only
STATUS mandatory
DESCRIPTION
	"Average time in microseconds (us), taken to complete a bridge operation."
::= {cacheEntry 8}

averageMSecPerCacheOperation OBJECT-TYPE
SYNTAX Counter64
ACCESS read-only
STATUS mandatory
DESCRIPTION
	"Average time in microseconds (us), taken to complete a cache operation."
::= {cacheEntry 9}

averageMSecPerFetch OBJECT-TYPE
SYNTAX Counter64
ACCESS read-only
STATUS mandatory
DESCRIPTION
	"Average time in microseconds (us), taken to complete get operation."
::= {cacheEntry 10}	

averageMSecPerFetchBulk OBJECT-TYPE
SYNTAX Counter64
ACCESS read-only
STATUS mandatory
DESCRIPTION
	"Average time in microseconds (us), taken to complete bulk get operation."
::= {cacheEntry 11}	

averageMSecPerInsert OBJECT-TYPE
SYNTAX Counter64
ACCESS read-only
STATUS mandatory
DESCRIPTION
	"Average time in microseconds (us), taken to complete insert operation."
::= {cacheEntry 12}	

averageMSecPerInsertBulk OBJECT-TYPE
SYNTAX Counter64
ACCESS read-only
STATUS mandatory
DESCRIPTION
	"Average time in microseconds (us), taken to complete bulk insert operation."
::= {cacheEntry 13}	

averageMSecPerRemove OBJECT-TYPE
SYNTAX Counter64
ACCESS read-only
STATUS mandatory
DESCRIPTION
	"Average time in microseconds (us), taken to complete remove operation."
::= {cacheEntry 14}	

averageMSecPerRemoveBulk OBJECT-TYPE
SYNTAX Counter64
ACCESS read-only
STATUS mandatory
DESCRIPTION
	"Average time in microseconds (us), taken to complete bulk remove operation."
::= {cacheEntry 15}	

cacheSize OBJECT-TYPE
SYNTAX Counter64
ACCESS read-only
STATUS mandatory
DESCRIPTION
	"Size of cache im MB's occpuied by items in the cache."
::= {cacheEntry 16}	

cacheCount OBJECT-TYPE
SYNTAX Counter64
ACCESS read-only
STATUS mandatory
DESCRIPTION
	"Number of items in cache."
::= {cacheEntry 17}	

dictionaryCount OBJECT-TYPE
SYNTAX Counter64
ACCESS read-only
STATUS mandatory
DESCRIPTION
	"Number of Dictionaries in the cache."
::= {cacheEntry 18}	

counterCount OBJECT-TYPE
SYNTAX Counter64
ACCESS read-only
STATUS mandatory
DESCRIPTION
	"Number of Counters in the cache."
::= {cacheEntry 19}	

counterSize OBJECT-TYPE
SYNTAX Counter64
ACCESS read-only
STATUS mandatory
DESCRIPTION
	"Size of the Counters in cache in bytes, including cache store meta info and all other indices."
::= {cacheEntry 20}	

deletesPerSec OBJECT-TYPE
SYNTAX Counter64
ACCESS read-only
STATUS mandatory
DESCRIPTION
	"Number of Remove operations per second."
::= {cacheEntry 21}	

messageStoreSize OBJECT-TYPE
SYNTAX Counter64
ACCESS read-only
STATUS mandatory
DESCRIPTION
	"Size of message store in bytes, including message store meta info."
::= {cacheEntry 22}	

messagesCount OBJECT-TYPE
SYNTAX Counter64
ACCESS read-only
STATUS mandatory
DESCRIPTION
	"Number of messages in the cache."
::= {cacheEntry 23}	

expirationIndexSize OBJECT-TYPE
SYNTAX Counter64
ACCESS read-only
STATUS mandatory
DESCRIPTION
	"Size of expiration in bytes, indices defined on the cache."
::= {cacheEntry 24}	

expirationsPerSec  OBJECT-TYPE
SYNTAX Counter64
ACCESS read-only
STATUS mandatory
DESCRIPTION
	"Number of items being expired currently per second."
::= {cacheEntry 25}	

fetchesPerSec OBJECT-TYPE
SYNTAX Counter64
ACCESS read-only
STATUS mandatory
DESCRIPTION
	"Number of Get operations per second."
::= {cacheEntry 26}	

requestsPerSec OBJECT-TYPE
SYNTAX Counter64
ACCESS read-only
STATUS mandatory
DESCRIPTION
	"Number of requests received (meaning cache commands like add, get, insert, remove etc.) from all clients to this cache server."
::= {cacheEntry 27}	

updatesPerSec OBJECT-TYPE
SYNTAX Counter64
ACCESS read-only
STATUS mandatory
DESCRIPTION
	"Number of Insert operations per second."
::= {cacheEntry 28}	

averageMSecPerQueryExecution OBJECT-TYPE
SYNTAX Counter64
ACCESS read-only
STATUS mandatory
DESCRIPTION
	"Average time in microseconds(us) query takes while executing."
::= {cacheEntry 29}	

averageMSecPerDataSourceUpdate OBJECT-TYPE
SYNTAX Counter64
ACCESS read-only
STATUS mandatory
DESCRIPTION
	"Average time, in microseconds (us), taken to complete one datasource update cache operation."
::= {cacheEntry 30}	

averageMSecPerDataSourceWrite  OBJECT-TYPE
SYNTAX Counter64
ACCESS read-only
STATUS mandatory
DESCRIPTION
	" Average time, in microseconds (us), taken to complete one datasource write operation. Datasource write operations include both write-thru and write-behind operations."
::= {cacheEntry 31}

numberOfClients OBJECT-TYPE
SYNTAX Counter64
ACCESS read-only
STATUS mandatory
DESCRIPTION
	"Number of connected clients to an instance of cache."
::= {cacheEntry 32}	

averageQuerySize  OBJECT-TYPE
SYNTAX Counter64
ACCESS read-only
STATUS mandatory
DESCRIPTION
	"Average number of items returned by queries in a second."
::= {cacheEntry 33}

averageMSecPerReadThru OBJECT-TYPE
SYNTAX Counter64
ACCESS read-only
STATUS mandatory
DESCRIPTION
	"Average time in microseconds, taken to complete Read thru operation."
::= {cacheEntry 34}	

averageMSecPerWriteBehind  OBJECT-TYPE
SYNTAX Counter64
ACCESS read-only
STATUS mandatory
DESCRIPTION
	"Average time in microseconds, taken to complete write behind operation."
::= {cacheEntry 35}

averageMSecWriteThru OBJECT-TYPE
SYNTAX Counter64
ACCESS read-only
STATUS mandatory
DESCRIPTION
	"Average time in microseconds, taken to complete write thru operation."
::= {cacheEntry 36}	

bCastQueueCount  OBJECT-TYPE
SYNTAX Counter64
ACCESS read-only
STATUS mandatory
DESCRIPTION
	"Number of items in BCast queue waiting to be processed on sequence."
::= {cacheEntry 37}

bridgeOperationsReceived OBJECT-TYPE
SYNTAX Counter64
ACCESS read-only
STATUS mandatory
DESCRIPTION
	"Number of bridge operations received."
::= {cacheEntry 38}	

bridgeOperationsReceivedPerSec  OBJECT-TYPE
SYNTAX Counter64
ACCESS read-only
STATUS mandatory
DESCRIPTION
	"Bridge operation received per sec."
::= {cacheEntry 39}

bridgeOperationsSent OBJECT-TYPE
SYNTAX Counter64
ACCESS read-only
STATUS mandatory
DESCRIPTION
	"Number of bridge operations sent."
::= {cacheEntry 40}	

bridgeOperationsSentPerSec  OBJECT-TYPE
SYNTAX Counter64
ACCESS read-only
STATUS mandatory
DESCRIPTION
	"Bridge operation sent per sec."
::= {cacheEntry 41}

bridgeQueueCount OBJECT-TYPE
SYNTAX Counter64
ACCESS read-only
STATUS mandatory
DESCRIPTION
	"Number of items in the bridge queue."
::= {cacheEntry 42}	

bridgeQueueSize  OBJECT-TYPE
SYNTAX Counter64
ACCESS read-only
STATUS mandatory
DESCRIPTION
	"Total size of bridge queue in bytes."
::= {cacheEntry 43}

bytesReceivedPerSec OBJECT-TYPE
SYNTAX Counter64
ACCESS read-only
STATUS mandatory
DESCRIPTION
	"Number of bytes received per second from other nodes of the cluster."
::= {cacheEntry 44}	

bytesSentPerSec  OBJECT-TYPE
SYNTAX Counter64
ACCESS read-only
STATUS mandatory
DESCRIPTION
	"Number of bytes sent per second to other nodes of the cluster."
::= {cacheEntry 45}

cacheLastAccessCount OBJECT-TYPE
SYNTAX Counter64
ACCESS read-only
STATUS mandatory
DESCRIPTION
	"Number of items which are older then the access interval specified in the service config file."
::= {cacheEntry 46}	

clientBytesReceivedPerSec  OBJECT-TYPE
SYNTAX Counter64
ACCESS read-only
STATUS mandatory
DESCRIPTION
	"Bytes being received by cache server from all its clients."
::= {cacheEntry 47}

clientBytesSentPerSec OBJECT-TYPE
SYNTAX Counter64
ACCESS read-only
STATUS mandatory
DESCRIPTION
	"Bytes being sent from cache server to all its clients."
::= {cacheEntry 48}	

clientRequestsPerSec  OBJECT-TYPE
SYNTAX Counter64
ACCESS read-only
STATUS mandatory
DESCRIPTION
	"Number of requests sent by all clients to the cache server."
::= {cacheEntry 49}

clientResponsesPerSec OBJECT-TYPE
SYNTAX Counter64
ACCESS read-only
STATUS mandatory
DESCRIPTION
	"Number of responses received by all clients from the cache server."
::= {cacheEntry 50}	

clusterOpsPerSec  OBJECT-TYPE
SYNTAX Counter64
ACCESS read-only
STATUS mandatory
DESCRIPTION
	"Number of clustered operations performed per second."
::= {cacheEntry 51}

clusteredOpsRecvedPerSec OBJECT-TYPE
SYNTAX Counter64
ACCESS read-only
STATUS mandatory
DESCRIPTION
	"Number of clustered operations received from other nodes in cluster per second."
::= {cacheEntry 52}	

clusteredOperationsSentPerSec  OBJECT-TYPE
SYNTAX Counter64
ACCESS read-only
STATUS mandatory
DESCRIPTION
	"Number of clustered operations sent to other nodes in cluster per second."
::= {cacheEntry 53}

dataBalancePerSec  OBJECT-TYPE
SYNTAX Counter64
ACCESS read-only
STATUS mandatory
DESCRIPTION
	"Number of items this node is either reading from other nodes or sending to other nodes during a Data Load Balancing mode."
::= {cacheEntry 54}

dataSourceFailedOperationsPerSec  OBJECT-TYPE
SYNTAX Counter64
ACCESS read-only
STATUS mandatory
DESCRIPTION
	"Number of datasource write operations failed per second. Write operations performed on datasource provider returning Failure/FailureRetry/FailureDontRemove as status of OperationResult are counted."
::= {cacheEntry 55}

dataSourceUpdatesPerSec  OBJECT-TYPE
SYNTAX Counter64
ACCESS read-only
STATUS mandatory
DESCRIPTION
	"Number of update operations per second in cache after datasource write operations."
::= {cacheEntry 56}

dictionarySize  OBJECT-TYPE
SYNTAX Counter64
ACCESS read-only
STATUS mandatory
DESCRIPTION
	"Number of Dictionaries in the cache."
::= {cacheEntry 57}

dispatchEnterPerSec  OBJECT-TYPE
SYNTAX Counter64
ACCESS read-only
STATUS mandatory
DESCRIPTION
	"Number of items in BCast queue waiting to be processed on sequence."
::= {cacheEntry 58}

eventQueueCount  OBJECT-TYPE
SYNTAX Counter64
ACCESS read-only
STATUS mandatory
DESCRIPTION
	"Number of items in event queue."
::= {cacheEntry 59}

evictionIndexSize  OBJECT-TYPE
SYNTAX Counter64
ACCESS read-only
STATUS mandatory
DESCRIPTION
	"Size of eviction indices in bytes, define on the cache."
::= {cacheEntry 60}

evictionsPerSec  OBJECT-TYPE
SYNTAX Counter64
ACCESS read-only
STATUS mandatory
DESCRIPTION
	"Number of items evicted per second."
::= {cacheEntry 61}

generalNotificationsQueueSize  OBJECT-TYPE
SYNTAX Counter64
ACCESS read-only
STATUS mandatory
DESCRIPTION
	"Number of general notification events in queue."
::= {cacheEntry 62}

groupIndexSize  OBJECT-TYPE
SYNTAX Counter64
ACCESS read-only
STATUS mandatory
DESCRIPTION
	"Size of group and sub group indices in bytes defined on this cache."
::= {cacheEntry 63}

hitsRatioPerSec  OBJECT-TYPE
SYNTAX Counter64
ACCESS read-only
STATUS mandatory
DESCRIPTION
	"Ratio of number of successful Get operations per second and total number of Get operations per second."
::= {cacheEntry 64}

hitsPerSec  OBJECT-TYPE
SYNTAX Counter64
ACCESS read-only
STATUS mandatory
DESCRIPTION
	"Number of successful Get operations per second."
::= {cacheEntry 65}

listCount  OBJECT-TYPE
SYNTAX Counter64
ACCESS read-only
STATUS mandatory
DESCRIPTION
	"Number of Lists in the cache."
::= {cacheEntry 66}

listSize  OBJECT-TYPE
SYNTAX Counter64
ACCESS read-only
STATUS mandatory
DESCRIPTION
	"Size of the Lists in cache in bytes, including cache store meta info and all other indices."
::= {cacheEntry 67}

loggedRequestCount  OBJECT-TYPE
SYNTAX Counter64
ACCESS read-only
STATUS mandatory
DESCRIPTION
	"Total number of currently logged requests."
::= {cacheEntry 68}

mapReduceCombinedPerSec  OBJECT-TYPE
SYNTAX Counter64
ACCESS read-only
STATUS mandatory
DESCRIPTION
	"Number of records Combined per sec."
::= {cacheEntry 69}

mapReduceMappedPerSec  OBJECT-TYPE
SYNTAX Counter64
ACCESS read-only
STATUS mandatory
DESCRIPTION
	"Number of records Mapped per sec."
::= {cacheEntry 70}

mapReduceReducedPerSec  OBJECT-TYPE
SYNTAX Counter64
ACCESS read-only
STATUS mandatory
DESCRIPTION
	"Number of records Reduced per sec."
::= {cacheEntry 71}

mapReduceRunningTasks  OBJECT-TYPE
SYNTAX Counter64
ACCESS read-only
STATUS mandatory
DESCRIPTION
	"Number of MapReduce tasks running."
::= {cacheEntry 72}

mapReduceWaitingTasks  OBJECT-TYPE
SYNTAX Counter64
ACCESS read-only
STATUS mandatory
DESCRIPTION
	"Number of MapReduce tasks waiting to be executed."
::= {cacheEntry 73}

mCastQueueCount  OBJECT-TYPE
SYNTAX Counter64
ACCESS read-only
STATUS mandatory
DESCRIPTION
	"Number of items in MCast queue waiting to be processed on sequence."
::= {cacheEntry 74}

messagesDeliveredPerSec  OBJECT-TYPE
SYNTAX Counter64
ACCESS read-only
STATUS mandatory
DESCRIPTION
	"Number of messages delivered to subsribers per second."
::= {cacheEntry 75}

messagesExpiredPerSec  OBJECT-TYPE
SYNTAX Counter64
ACCESS read-only
STATUS mandatory
DESCRIPTION
	"Number of messages expired per second."
::= {cacheEntry 76}

messagesPublishedPerSec  OBJECT-TYPE
SYNTAX Counter64
ACCESS read-only
STATUS mandatory
DESCRIPTION
	"Number of messages published per second."
::= {cacheEntry 77}

mirrorQueueSize  OBJECT-TYPE
SYNTAX Counter64
ACCESS read-only
STATUS mandatory
DESCRIPTION
	"Number of items in the Mirror queue."
::= {cacheEntry 78}

missesPerSec  OBJECT-TYPE
SYNTAX Counter64
ACCESS read-only
STATUS mandatory
DESCRIPTION
	"Number of failed Get operations per second."
::= {cacheEntry 79}

naglingMsgCount  OBJECT-TYPE
SYNTAX Counter64
ACCESS read-only
STATUS mandatory
DESCRIPTION
	"Time in milli seconds for which a sequenced messages waits before it is processed."
::= {cacheEntry 80}

queriesPerSec  OBJECT-TYPE
SYNTAX Counter64
ACCESS read-only
STATUS mandatory
DESCRIPTION
	"Number of queries executing per sec on the cache."
::= {cacheEntry 81}

queryIndexSize  OBJECT-TYPE
SYNTAX Counter64
ACCESS read-only
STATUS mandatory
DESCRIPTION
	"Size of query indices in bytes, defined on the cache."
::= {cacheEntry 82}

queueCount  OBJECT-TYPE
SYNTAX Counter64
ACCESS read-only
STATUS mandatory
DESCRIPTION
	"Number of Queues in the cache."
::= {cacheEntry 83}

queueSize  OBJECT-TYPE
SYNTAX Counter64
ACCESS read-only
STATUS mandatory
DESCRIPTION
	"Size of the Queues in cache in bytes, including cache store meta info and all other indices."
::= {cacheEntry 84}

readersCount  OBJECT-TYPE
SYNTAX Counter64
ACCESS read-only
STATUS mandatory
DESCRIPTION
	"Number of running readers."
::= {cacheEntry 85}

readThruPerSec  OBJECT-TYPE
SYNTAX Counter64
ACCESS read-only
STATUS mandatory
DESCRIPTION
	"Number of Read-thru operations per second."
::= {cacheEntry 86}

requestLogLedgerSize  OBJECT-TYPE
SYNTAX Counter64
ACCESS read-only
STATUS mandatory
DESCRIPTION
	"Total in-memory size of the log ledger, which stores logged requests."
::= {cacheEntry 87}

requestsLoggedPerSec  OBJECT-TYPE
SYNTAX Counter64
ACCESS read-only
STATUS mandatory
DESCRIPTION
	"Average number of requests logged in a second."
::= {cacheEntry 88}

responseQueueCount  OBJECT-TYPE
SYNTAX Counter64
ACCESS read-only
STATUS mandatory
DESCRIPTION
	"Number of items in response queue."
::= {cacheEntry 89}

responseQueueSize  OBJECT-TYPE
SYNTAX Counter64
ACCESS read-only
STATUS mandatory
DESCRIPTION
	"Size of response queue specified in bytes."
::= {cacheEntry 90}

responseSentPerSec  OBJECT-TYPE
SYNTAX Counter64
ACCESS read-only
STATUS mandatory
DESCRIPTION
	"Number of responses sent to other nodes in cluster per second."
::= {cacheEntry 91}

responsesPerSec  OBJECT-TYPE
SYNTAX Counter64
ACCESS read-only
STATUS mandatory
DESCRIPTION
	"Number of responses sent (meaning cache response for commands like add, get, insert, remove etc.) to all clients by this cache server."
::= {cacheEntry 92}

setCount  OBJECT-TYPE
SYNTAX Counter64
ACCESS read-only
STATUS mandatory
DESCRIPTION
	"Number of Sets in the cache."
::= {cacheEntry 93}

setSize  OBJECT-TYPE
SYNTAX Counter64
ACCESS read-only
STATUS mandatory
DESCRIPTION
	"Size of the Sets in cache in bytes, including cache store meta info and all other indices."
::= {cacheEntry 94}

slidingIndexqueuesize  OBJECT-TYPE
SYNTAX Counter64
ACCESS read-only
STATUS mandatory
DESCRIPTION
	"Number of items in the Sliding-Index queue."
::= {cacheEntry 95}

socketRecvSize  OBJECT-TYPE
SYNTAX Counter64
ACCESS read-only
STATUS mandatory
DESCRIPTION
	"How much data was received in the last message."
::= {cacheEntry 96}

socketRecvtime  OBJECT-TYPE
SYNTAX Counter64
ACCESS read-only
STATUS mandatory
DESCRIPTION
	"Time in milli seconds it took to receive the last message."
::= {cacheEntry 97}

socketSendSize  OBJECT-TYPE
SYNTAX Counter64
ACCESS read-only
STATUS mandatory
DESCRIPTION
	"How much data was sent in the last message."
::= {cacheEntry 98}

socketSendTime  OBJECT-TYPE
SYNTAX Counter64
ACCESS read-only
STATUS mandatory
DESCRIPTION
	"Time in milli seconds it took for the last message to be sent over the socket."
::= {cacheEntry 99}

stateTransferPerSec  OBJECT-TYPE
SYNTAX Counter64
ACCESS read-only
STATUS mandatory
DESCRIPTION
	"Number of items this node is either reading from other nodes or sending to other nodes during a state transfer mode."
::= {cacheEntry 100}

tcpDownEnterPerSec  OBJECT-TYPE
SYNTAX Counter64
ACCESS read-only
STATUS mandatory
DESCRIPTION
	"Number of items in BCast queue waiting to be processed on sequence."
::= {cacheEntry 101}

tcpDownQueueCount  OBJECT-TYPE
SYNTAX Counter64
ACCESS read-only
STATUS mandatory
DESCRIPTION
	"Number of items in TCP down-queue."
::= {cacheEntry 102}

tcpUpQueueCount  OBJECT-TYPE
SYNTAX Counter64
ACCESS read-only
STATUS mandatory
DESCRIPTION
	"Number of items in TCP up-queue."
::= {cacheEntry 103}

topicsCount  OBJECT-TYPE
SYNTAX Counter64
ACCESS read-only
STATUS mandatory
DESCRIPTION
	"Number of Topics in the cache."
::= {cacheEntry 104}

writeBehindBatchCount  OBJECT-TYPE
SYNTAX Counter64
ACCESS read-only
STATUS mandatory
DESCRIPTION
	"Number of operations selected in current batch interval for execution. For write-behind, if batching is enabled, number of operations dequeued in current batch interval for execution is displayed by this counter."
::= {cacheEntry 105}

writeBehindEvictionsPerSec  OBJECT-TYPE
SYNTAX Counter64
ACCESS read-only
STATUS mandatory
DESCRIPTION
	"Number of items evicted per second from write-behind queue. Only failed operation are evicted which are enqueued for operation retry."
::= {cacheEntry 106}

writeBehindFailureRetrycount  OBJECT-TYPE
SYNTAX Counter64
ACCESS read-only
STATUS mandatory
DESCRIPTION
	"Number of operations failed enqueued for retry. Data source write operation returning FailureRetry as status are also enqueued for retry."
::= {cacheEntry 107}

writeBehindQueueCount  OBJECT-TYPE
SYNTAX Counter64
ACCESS read-only
STATUS mandatory
DESCRIPTION
	"Number of operations in Write-behind queue."
::= {cacheEntry 108}

writeBehindPerSec  OBJECT-TYPE
SYNTAX Counter64
ACCESS read-only
STATUS mandatory
DESCRIPTION
	"Number of Write-behind operations per second."
::= {cacheEntry 109}

writeThruPerSec  OBJECT-TYPE
SYNTAX Counter64
ACCESS read-only
STATUS mandatory
DESCRIPTION
	"Number of Write-thru operations per second."
::= {cacheEntry 110}

totalCacheSize  OBJECT-TYPE
SYNTAX Counter64
ACCESS read-only
STATUS mandatory
DESCRIPTION
	"Total size of the cache."
::= {cacheEntry 111}

configuredServersCount  OBJECT-TYPE
SYNTAX Counter64
ACCESS read-only
STATUS mandatory
DESCRIPTION
	"Total number of configured servers against the cache."
::= {cacheEntry 112}

averageMSecPerAdd OBJECT-TYPE
SYNTAX Counter64
ACCESS read-only
STATUS mandatory
DESCRIPTION
	"Average time in microseconds (us), taken to complete one add operation."
::= {cacheEntry 113}

-------------Persistence Counters----------------


persistQCount  OBJECT-TYPE
SYNTAX Counter64
ACCESS read-only
STATUS mandatory
DESCRIPTION
	"Number of operations in persistence queue."
::= {cacheEntry 114}

persistQSize  OBJECT-TYPE
SYNTAX Counter64
ACCESS read-only
STATUS mandatory
DESCRIPTION
	"Size of persistence queue specified in bytes."
::= {cacheEntry 115}

dbReadsPerSec  OBJECT-TYPE
SYNTAX Counter64
ACCESS read-only
STATUS mandatory
DESCRIPTION
	"Number of persistence read operations per second."
::= {cacheEntry 116}

dbWritesPerSec  OBJECT-TYPE
SYNTAX Counter64
ACCESS read-only
STATUS mandatory
DESCRIPTION
	"Number of persistence write operations per second."
::= {cacheEntry 117}

averageMsecPerDbRead  OBJECT-TYPE
SYNTAX Counter64
ACCESS read-only
STATUS mandatory
DESCRIPTION
	"Average time in milliseconds, taken to complete persistence read operations."
::= {cacheEntry 118}

averageMsecPerDbWrite  OBJECT-TYPE
SYNTAX Counter64
ACCESS read-only
STATUS mandatory
DESCRIPTION
	"Average time in milliseconds, taken to complete persistence write operations."
::= {cacheEntry 119}

lastDbReadTime  OBJECT-TYPE
SYNTAX Counter64
ACCESS read-only
STATUS mandatory
DESCRIPTION
	"The timestamp telling the last time data was read/loaded from persistence store."
::= {cacheEntry 120}

lastDbWriteTime  OBJECT-TYPE
SYNTAX Counter64
ACCESS read-only
STATUS mandatory
DESCRIPTION
	"The timestamp telling the last time data was flushed to persistence store."
::= {cacheEntry 121}

-------------Lucene Counters----------------

replicationQueueCount  OBJECT-TYPE
SYNTAX Counter64
ACCESS read-only
STATUS mandatory
DESCRIPTION
	"Number of replication operations of writer currently in queue."
::= {cacheEntry 122}

indexes  OBJECT-TYPE
SYNTAX Counter64
ACCESS read-only
STATUS mandatory
DESCRIPTION
	"Total number of indexes created by user."
::= {cacheEntry 123}

liveInstances  OBJECT-TYPE
SYNTAX Counter64
ACCESS read-only
STATUS mandatory
DESCRIPTION
	"Total number of instances instantiated by client."
::= {cacheEntry 124}

documents  OBJECT-TYPE
SYNTAX Counter64
ACCESS read-only
STATUS mandatory
DESCRIPTION
	"Total number of documents inserted."
::= {cacheEntry 125}

indexSize  OBJECT-TYPE
SYNTAX Counter64
ACCESS read-only
STATUS mandatory
DESCRIPTION
	"Total size of all indices in bytes."
::= {cacheEntry 126}

commits  OBJECT-TYPE
SYNTAX Counter64
ACCESS read-only
STATUS mandatory
DESCRIPTION
	"Number of commits in the module."
::= {cacheEntry 127}

bucketsToSend  OBJECT-TYPE
SYNTAX Counter64
ACCESS read-only
STATUS mandatory
DESCRIPTION
	"Number of buckets that need to be sent to other nodes."
::= {cacheEntry 128}

bucketsToReceive  OBJECT-TYPE
SYNTAX Counter64
ACCESS read-only
STATUS mandatory
DESCRIPTION
	"Number of buckets that need to be received from other nodes."
::= {cacheEntry 129}

lucene_updatesPerSec  OBJECT-TYPE
SYNTAX Counter64
ACCESS read-only
STATUS mandatory
DESCRIPTION
	"Number of Update operations per second."
::= {cacheEntry 130}

searchesPerSec  OBJECT-TYPE
SYNTAX Counter64
ACCESS read-only
STATUS mandatory
DESCRIPTION
	"Number of Search operations per second."
::= {cacheEntry 131}

additionsPerSec  OBJECT-TYPE
SYNTAX Counter64
ACCESS read-only
STATUS mandatory
DESCRIPTION
	"Number of Add operations per second."
::= {cacheEntry 132}

lucene_fetchesPerSec  OBJECT-TYPE
SYNTAX Counter64
ACCESS read-only
STATUS mandatory
DESCRIPTION
	"Number of Fetch/Read operations per second."
::= {cacheEntry 133}

lucene_deletesPerSec  OBJECT-TYPE
SYNTAX Counter64
ACCESS read-only
STATUS mandatory
DESCRIPTION
	"Number of Delete operations per second."
::= {cacheEntry 134}

lucene_stateTransferPerSec  OBJECT-TYPE
SYNTAX Counter64
ACCESS read-only
STATUS mandatory
DESCRIPTION
	"Size of data this node is either reading from other nodes or sending to other nodes during a state transfer operation."
::= {cacheEntry 135}

avgMsecPerSearch  OBJECT-TYPE
SYNTAX Counter64
ACCESS read-only
STATUS mandatory
DESCRIPTION
	"Average time in milliseconds, taken to complete one search operation."
::= {cacheEntry 136}

avgMsecPerFetch  OBJECT-TYPE
SYNTAX Counter64
ACCESS read-only
STATUS mandatory
DESCRIPTION
	"Average time in milliseconds, taken to complete one fetch operation."
::= {cacheEntry 137}

avgMsecPerAdd  OBJECT-TYPE
SYNTAX Counter64
ACCESS read-only
STATUS mandatory
DESCRIPTION
	"Average time in milliseconds, taken to complete one add operation."
::= {cacheEntry 138}

avgMsecPerUpdate  OBJECT-TYPE
SYNTAX Counter64
ACCESS read-only
STATUS mandatory
DESCRIPTION
	"Average time in milliseconds, taken to complete one update operation."
::= {cacheEntry 139}

avgMsecPerDelete  OBJECT-TYPE
SYNTAX Counter64
ACCESS read-only
STATUS mandatory
DESCRIPTION
	"Average time in milliseconds, taken to complete one delete operation."
::= {cacheEntry 140}

lucene_requestsPerSec  OBJECT-TYPE
SYNTAX Counter64
ACCESS read-only
STATUS mandatory
DESCRIPTION
	"Number of requests received by the distributed module."
::= {cacheEntry 141}



-------------Client Counters Table----------------
clientTable OBJECT-TYPE
      SYNTAX      SEQUENCE OF ClientEntry
      MAX-ACCESS  not-accessible
      STATUS      current
      DESCRIPTION
              "A list of interface entries.  The number of entries
               is given by the value of ifNumber."
       ::= { client 1 }
clientEntry OBJECT-TYPE
     SYNTAX      ClientEntry
     MAX-ACCESS  not-accessible
     STATUS      current
     DESCRIPTION
             "An entry containing management information applicable
             to a particular interface."
     INDEX   { clientIndex }
     ::= { clientTable 1 }
	 

ClientEntry ::=
    SEQUENCE {
        clientIndex                       Integer32 ,
        client_cacheName                         DisplayString,
		client_cacheConfigId                     DisplayString,
		bindIP                            DisplayString,
		client_fetchesPerSec                     Counter64,
		client_additionPerSec                    Counter64,
		client_updatesPerSec                     Counter64,
		client_deletesPerSec                     Counter64,
		readOperationsPerSec              Counter64,
		writeOperationsPerSec             Counter64,
		client_averageMSecPerFetch               Counter64,
		client_averageMSecPerAdd                 Counter64,
		client_averageMSecPerInsert              Counter64,
		client_averageMSecPerRemove              Counter64,
		requestQueueSize                  Counter64,
		compressionsPerSec                Counter64,
		averageItemSize                   Counter64,
		averageMSecPerEvent               Counter64,
		eventsProcessedPerSec             Counter64,
		eventsTriggeredPerSec             Counter64,
		averageMSecPerCompression         Counter64,
		averageMSecPerDecompression       Counter64,
		averageMSecPerEncryption          Counter64,
		averageMSecPerDecryption          Counter64,
		averageCompressedItemSize         Counter64,
		averageMSecPerSerialization       Counter64,
		averageMSecPerDeserialization     Counter64,
		averageMSecPerAddbulk             Counter64,
		averageMSecPerFetchbulk           Counter64,
		averageMSecPerInsertbulk          Counter64,
		averageMSecPerRemovebulk          Counter64,
		numberOfLastSyncPollUpdates       Counter64,
		numberOfLastSyncPollRemoves       Counter64,
		averageMSecPerPublishedMessages   Counter64,
		client_messagesPublishedPerSec           Counter64,
		client_messagesDeliveredPerSec           Counter64
	}

clientIndex OBJECT-TYPE
    SYNTAX      Integer32 
    MAX-ACCESS  read-only
    STATUS      current
    DESCRIPTION
            "A unique value, greater than zero, for each cache."
    ::= { clientEntry 1 }
client_cacheName  OBJECT-TYPE
SYNTAX DisplayString
ACCESS read-only
STATUS mandatory
DESCRIPTION
	"Name of the cache to which client is connected."
::= {clientEntry 2}

client_cacheConfigId  OBJECT-TYPE
SYNTAX DisplayString
ACCESS read-only
STATUS mandatory
DESCRIPTION
	"Config-ID of the cache to which client is connected."
::= {clientEntry 3}

bindIP  OBJECT-TYPE
SYNTAX DisplayString
ACCESS read-only
STATUS mandatory
DESCRIPTION
	""
::= {clientEntry 4}

client_fetchesPerSec  OBJECT-TYPE
SYNTAX Counter64
ACCESS read-only
STATUS mandatory
DESCRIPTION
	"Number of Get operations per second."
::= {clientEntry 5}

client_additionPerSec  OBJECT-TYPE
SYNTAX Counter64
ACCESS read-only
STATUS mandatory
DESCRIPTION
	"Number of Add operations per second."
::= {clientEntry 6}

client_updatesPerSec  OBJECT-TYPE
SYNTAX Counter64
ACCESS read-only
STATUS mandatory
DESCRIPTION
	"Number of Insert operations per second."
::= {clientEntry 7}

client_deletesPerSec  OBJECT-TYPE
SYNTAX Counter64
ACCESS read-only
STATUS mandatory
DESCRIPTION
	"Number of Remove operations per second."
::= {clientEntry 8}

readOperationsPerSec  OBJECT-TYPE
SYNTAX Counter64
ACCESS read-only
STATUS mandatory
DESCRIPTION
	"Number of Read operations per second."
::= {clientEntry 9}

writeOperationsPerSec  OBJECT-TYPE
SYNTAX Counter64
ACCESS read-only
STATUS mandatory
DESCRIPTION
	"Number of Write operations per second."
::= {clientEntry 10}

client_averageMSecPerFetch  OBJECT-TYPE
SYNTAX Counter64
ACCESS read-only
STATUS mandatory
DESCRIPTION
	"Average time in microseconds (us), taken to complete one fetch operation."
::= {clientEntry 11}

client_averageMSecPerAdd  OBJECT-TYPE
SYNTAX Counter64
ACCESS read-only
STATUS mandatory
DESCRIPTION
	"Average time in microseconds (us), taken to complete one add operation."
::= {clientEntry 12}

client_averageMSecPerInsert  OBJECT-TYPE
SYNTAX Counter64
ACCESS read-only
STATUS mandatory
DESCRIPTION
	"Average time in microseconds, taken to complete one insert operation."
::= {clientEntry 13}

client_averageMSecPerRemove  OBJECT-TYPE
SYNTAX Counter64
ACCESS read-only
STATUS mandatory
DESCRIPTION
	"Average time in microseconds (us), taken to complete one remove operation."
::= {clientEntry 14}

requestQueueSize  OBJECT-TYPE
SYNTAX Counter64
ACCESS read-only
STATUS mandatory
DESCRIPTION
	"Total number of requests from all clients on a single machine waiting for response from cache server."
::= {clientEntry 15}

compressionsPerSec  OBJECT-TYPE
SYNTAX Counter64
ACCESS read-only
STATUS mandatory
DESCRIPTION
	"Rate of compression/decompression i.e. how many items are compressed/decompression during one second interval."
::= {clientEntry 16}

averageItemSize  OBJECT-TYPE
SYNTAX Counter64
ACCESS read-only
STATUS mandatory
DESCRIPTION
	"Average size of the item added to/fetched from the cache by the client. Average size is calculated before compression/after decompression is applied."
::= {clientEntry 17}

averageMSecPerEvent  OBJECT-TYPE
SYNTAX Counter64
ACCESS read-only
STATUS mandatory
DESCRIPTION
	"Average time in microseconds (us), taken in single event processing on the client."
::= {clientEntry 18}

eventsProcessedPerSec  OBJECT-TYPE
SYNTAX Counter64
ACCESS read-only
STATUS mandatory
DESCRIPTION
	"Number of events processed per sec on client."
::= {clientEntry 19}

eventsTriggeredPerSec  OBJECT-TYPE
SYNTAX Counter64
ACCESS read-only
STATUS mandatory
DESCRIPTION
	"Number of events triggered and received by client per second."
::= {clientEntry 20}

averageMSecPerCompression  OBJECT-TYPE
SYNTAX Counter64
ACCESS read-only
STATUS mandatory
DESCRIPTION
	"Average time in microseconds (us), taken to compress one object."
::= {clientEntry 21}

averageMSecPerDecompression  OBJECT-TYPE
SYNTAX Counter64
ACCESS read-only
STATUS mandatory
DESCRIPTION
	"Average time in microseconds (us), taken to decompress one object."
::= {clientEntry 22}

averageMSecPerEncryption  OBJECT-TYPE
SYNTAX Counter64
ACCESS read-only
STATUS mandatory
DESCRIPTION
	"Average time in microseconds (us), taken to encrypt one object."
::= {clientEntry 23}

averageMSecPerDecryption  OBJECT-TYPE
SYNTAX Counter64
ACCESS read-only
STATUS mandatory
DESCRIPTION
	"Average time in microseconds (us), taken to decrypt one object."
::= {clientEntry 24}

averageCompressedItemSize  OBJECT-TYPE
SYNTAX Counter64
ACCESS read-only
STATUS mandatory
DESCRIPTION
	"Average size in bytes, item size after compression on add or item size before decompression on fetch."
::= {clientEntry 25}

averageMSecPerSerialization  OBJECT-TYPE
SYNTAX Counter64
ACCESS read-only
STATUS mandatory
DESCRIPTION
	"Average time in microseconds (us), taken to serialize one object."
::= {clientEntry 26}

averageMSecPerDeserialization  OBJECT-TYPE
SYNTAX Counter64
ACCESS read-only
STATUS mandatory
DESCRIPTION
	"Average time in microseconds (us), taken to deserialize one object."
::= {clientEntry 27}

averageMSecPerAddbulk  OBJECT-TYPE
SYNTAX Counter64
ACCESS read-only
STATUS mandatory
DESCRIPTION
	"Average time in microseconds (us), taken to complete bulk add operation."
::= {clientEntry 28}

averageMSecPerFetchbulk  OBJECT-TYPE
SYNTAX Counter64
ACCESS read-only
STATUS mandatory
DESCRIPTION
	"Average time in microseconds (us), taken to complete bulk get operation."
::= {clientEntry 29}

averageMSecPerInsertbulk  OBJECT-TYPE
SYNTAX Counter64
ACCESS read-only
STATUS mandatory
DESCRIPTION
	"Average time in microseconds (us), taken to complete bulk insert operation."
::= {clientEntry 30}

averageMSecPerRemovebulk  OBJECT-TYPE
SYNTAX Counter64
ACCESS read-only
STATUS mandatory
DESCRIPTION
	"Average time in microseconds (us), taken to complete bulk remove operation."
::= {clientEntry 31}

numberOfLastSyncPollUpdates  OBJECT-TYPE
SYNTAX Counter64
ACCESS read-only
STATUS mandatory
DESCRIPTION
	"Number of Updates resulted in last Sync Poll."
::= {clientEntry 32}

numberOfLastSyncPollRemoves  OBJECT-TYPE
SYNTAX Counter64
ACCESS read-only
STATUS mandatory
DESCRIPTION
	"Number of Removes resulted in last Sync Poll."
::= {clientEntry 33}

averageMSecPerPublishedMessages  OBJECT-TYPE
SYNTAX Counter64
ACCESS read-only
STATUS mandatory
DESCRIPTION
	"Average time in microseconds, taken to complete publish messages operation."
::= {clientEntry 34}

client_messagesPublishedPerSec  OBJECT-TYPE
SYNTAX Counter64
ACCESS read-only
STATUS mandatory
DESCRIPTION
	"Number of messages published per second."
::= {clientEntry 35}

client_messagesDeliveredPerSec  OBJECT-TYPE
SYNTAX Counter64
ACCESS read-only
STATUS mandatory
DESCRIPTION
	"Number of messages delivered to subsribers per second."
::= {clientEntry 36}


END
